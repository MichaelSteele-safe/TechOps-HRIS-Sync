FME workspace HR - UKG to Atlassian Teams Sync.fmw

Parameters:
- SLACK_NOTIFICATION_WEBHOOK = https://hooks.slack.com/services/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   # webhook to send notification to slack
- PREVIEW_MODE = NO   # Run in Preview Mode?

Writers:
- CSV2_1: CSV2 to /Users/ellaine.chan/Desktop

Note: UKG Generated reports are sent to hrisautomation@safe.com, picked up by Google App Scripts and dropped to Google Drive. This workspace reads the latest CSV files to migrate data into our database. / Author: Ellaine Chan
SQLCreator
    DATASET = IS FH SET DB
    EXPOSED_ATTRIBUTE_LIST = id,name,ukg_id
    FORMAT = POSTGRES
    OUTPUT_FEATURES = DATA_ONLY
    POSTGRES_CREATE_FEATURE_TABLES_FROM_DATA = Yes
    POSTGRES_NAMED_CONNECTION = IS FH SET DB
    POSTGRES_QUERY_FEATURE_TYPES_FOR_MERGE_FILTERS = Yes
    POSTGRES_READ_TIME_WITH_TIMEZONE = Yes
    SQL_STATEMENT = select * from public.atlassian_teams
    RESULT -> FeatureMerger_5 [REQUESTOR]
    RESULT -> FeatureMerger [SUPPLIER]
Note: Extract account ID
JSONExtractor_4
    EXTRACT_QUERY_TABLE = account_id json["accountId"]
    JSON_DOCUMENT = @Value(membership_list)
    READ_FROM_FILE = NO
    EVALUATED -> FeatureMerger_4 [REQUESTOR]
Note: Syncs Atlassian Teams using UKG data / Due to limitations in REST API (and very poorly documented GraphQL API as of Feb 2024) we are storing team ids in the IS FH database. This might not be needed in the future. / Author: Ellaine
SafeEmployeeReader
    -> AtlassianIDGetter [email]
AtlassianIDGetter
    EMAIL = @Value(email)
    -> Tester_3
Tester_3
    BOOL_OP = OR
    TEST_CLAUSE = TEST Atlassian Account ID ATTRIBUTE_HAS_A_VALUE ""
    TEST_MODE = TEST
    PASSED -> DuplicateFilter
    PASSED -> AttributeManager_2
    PASSED -> AttributeManager_3
    PASSED -> FeatureMerger_2 [REQUESTOR]
    PASSED -> ListBuilder_2
    PASSED -> FeatureMerger_4 [SUPPLIER]
Note: Add user info like first and last to each account id
FeatureMerger_4
    ATTR_ACCUM_MODE = Merge Supplier
    ATTR_CONFLICT_RES_LOOKUP = REQUESTOR_IF_CONFLICT
    IGNORE_NULLS = No
    JOIN_KEYS = @Value(account_id) @Value(Atlassian Account ID) AUTO
    MERGE_TYPE = Attributes Only
    PRESERVE_FEATURE_ORDER_LOOKUP = PER_OUTPUT_PORT
    PROCESS_DUPS = NO
    REJECT_NULL_MISSING_KEYS = No
    SUPPLIERS_FIRST = No
    ATTR_CONFLICT_RES = Use Requestor
    MERGED -> ListBuilder
    MERGED -> FeatureMerger_3 [REQUESTOR]
    UNMERGED_REQUESTOR -> ListBuilder

Bookmark: Get current UKG teams
Creator
    GEOMTYPE = Geometry Object
    NUM = 1
    CREATED -> HTTPCaller_10
HTTPCaller_10
    AUTH_METHOD_TYPE = NC
    AUTH_NAMED_CONNECTION = services.api.safe.com prod connection
    CLIENT_CERTIFICATE_TYPE = NONE
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://services.api.safe.com/v1/users/teams
    TRANSFER_TIMEOUT_LENGTH = 90
    USE_COOKIES = No
    VERIFY_SSL_CERTIFICATES = Yes
    AUTH_METHOD = Web Connection
    -> JSONFragmenter_2
JSONFragmenter_2
    EXPLODE_FORMAT = JSON
    EXTRACT_ATTR = No
    JSON_ATTR = _response_body
    JSON_QUERY = json[*]
    READ_FROM_FILE = NO
    REJECT_EMPTY_LISTS = YES
    FRAGMENTS -> JSONFlattener
JSONFlattener
    ERROR_LIST_ATTR = _json_error
    JSON_DOCUMENT = @Value(_response_body)
    NEW_ATTRIBUTES = ukg_id name alt_name
    READ_FROM_FILE = NO
    RECURSIVE_LOOKUP = YES
    RECURSIVE = Yes
    -> Tester_8
Tester_8
    BOOL_OP = OR
    TEST_CLAUSE = TEST alt_name ATTRIBUTE_HAS_A_VALUE ""
    TEST_MODE = TEST
    PASSED -> AttributeManager_5
    FAILED -> AttributeManager_4
AttributeManager_5
    ATTR_TABLE = SET_TO name (buffer) = @Value(alt_name)
    -> AttributeManager_4
AttributeManager_4
    ATTR_TABLE = RENAME_SET_VALUE name > ukg_name (buffer)
    -> FeatureMerger_5 [SUPPLIER]

Bookmark: Update team names if necessary
FeatureMerger_5
    ATTR_ACCUM_MODE = Merge Supplier
    ATTR_CONFLICT_RES_LOOKUP = REQUESTOR_IF_CONFLICT
    IGNORE_NULLS = No
    JOIN_KEYS = @Value(ukg_id) @Value(ukg_id) AUTO
    MERGE_TYPE = Attributes Only
    PRESERVE_FEATURE_ORDER_LOOKUP = PER_OUTPUT_PORT
    PROCESS_DUPS = NO
    REJECT_NULL_MISSING_KEYS = No
    SUPPLIERS_FIRST = No
    ATTR_CONFLICT_RES = Use Requestor
    MERGED -> Tester_7
Tester_7
    BOOL_OP = OR
    TEST_CLAUSE = TEST @Value(name) = @Value(ukg_name)
    TEST_MODE = TEST
    PASSED -> HTTPCaller_2
    FAILED -> HTTPCaller_12
Note: Update team name in Atlassian
HTTPCaller_12
    AUTH_METHOD_TYPE = NC
    AUTH_NAMED_CONNECTION = SET Atlassian Admin Header Connection
    CLIENT_CERTIFICATE_TYPE = NONE
    CONNECTION_TIMEOUT_LENGTH = 60
    CONTENT_TYPE_LOOKUP = application/json
    ERROR_ATTR = _error
    FOLLOW_REDIRECTS = FOLLOW_WITH_GET
    HTTP_METHOD = PATCH
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://safesoftware.atlassian.net/gateway/api/public/teams/v1/org/4f8ad3b0-d554-4c23-8f0b-1c57f5ee7e2a/teams/@Value(id)/
    TRANSFER_TIMEOUT_LENGTH = 90
    UPLOAD_BODY:
      {
          "displayName": "@Value(ukg_name)",
          "description": "Team @Value(ukg_name)"
      }
    UPLOAD_TYPE = Specify Upload Body
    USE_COOKIES = No
    VERIFY_SSL_CERTIFICATES = Yes
    AUTH_METHOD = Web Connection
    UPLOAD_CONTENT_TYPE = JSON (application/json)
    -> HTTPCaller_2
    -> SQLExecutor [INITIATOR]
SQLExecutor
    COMBINE_ATTRS = Result Attributes Only
    COMBINE_GEOM = Initiator Geometry Only
    DATASET = IS FH SET DB
    FORMAT = POSTGRES
    OUTPUT_FEATURES_DISPLAY = Schema and Data Features
    POSTGRES_CREATE_FEATURE_TABLES_FROM_DATA = Yes
    POSTGRES_NAMED_CONNECTION = IS FH SET DB
    POSTGRES_QUERY_FEATURE_TYPES_FOR_MERGE_FILTERS = Yes
    POSTGRES_READ_TIME_WITH_TIMEZONE = Yes
    SQL_STATEMENT:
      UPDATE public.atlassian_teams
      SET name = '@Value(ukg_name)'
      where id = '@Value(id)'

Bookmark: Get members currently in Team
Note: Get Team membership list
HTTPCaller_2
    AUTH_METHOD_TYPE = NC
    AUTH_NAMED_CONNECTION = SET Atlassian Admin Header Connection
    CLIENT_CERTIFICATE_TYPE = NONE
    CONNECTION_TIMEOUT_LENGTH = 60
    CONTENT_TYPE_LOOKUP = application/json
    CUSTOM_HEADERS = Accept;*/* Content-Type;application/json
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = team_membership_response
    TARGET_ATTR_ENCODING = auto-detect
    TARGET_URL = https://safesoftware.atlassian.net/gateway/api/public/teams/v1/org/4f8ad3b0-d554-4c23-8f0b-1c57f5ee7e2a/teams/@Value(id)/members
    TRANSFER_TIMEOUT_LENGTH = 90
    UPLOAD_TYPE = Specify Upload Body
    USE_COOKIES = No
    VERIFY_SSL_CERTIFICATES = Yes
    AUTH_METHOD = Web Connection
    UPLOAD_CONTENT_TYPE = JSON (application/json)
    -> JSONExtractor_5
    -> JSONExtractor_2
JSONExtractor_5
    EXTRACT_QUERY_TABLE = membership_list json["results"]
    JSON_DOCUMENT = @Value(team_membership_response)
    READ_FROM_FILE = NO
    EVALUATED -> JSONFragmenter
JSONFragmenter
    EXPLODE_FORMAT = JSON
    EXTRACT_ATTR = No
    JSON_ATTR = membership_list
    JSON_QUERY = json[*]
    READ_FROM_FILE = NO
    REJECT_EMPTY_LISTS = YES
    FRAGMENTS -> JSONExtractor_4

Bookmark: get second page
JSONExtractor_2
    EXTRACT_QUERY_TABLE = endCursor json["pageInfo"]["endCursor"] nextPage json["pageInfo"]["hasNextPage"]
    JSON_DOCUMENT = @Value(team_membership_response)
    READ_FROM_FILE = NO
    EVALUATED -> Tester_9
Tester_9
    BOOL_OP = OR
    TEST_CLAUSE = TEST @Value(nextPage) = true
    TEST_MODE = TEST
    PASSED -> HTTPCaller_13
HTTPCaller_13
    AUTH_METHOD_TYPE = NC
    AUTH_NAMED_CONNECTION = SET Atlassian Admin Header Connection
    CLIENT_CERTIFICATE_TYPE = NONE
    CONNECTION_TIMEOUT_LENGTH = 60
    CONTENT_TYPE_LOOKUP = application/json
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = team_membership_response
    TARGET_ATTR_ENCODING = auto-detect
    TARGET_URL = https://safesoftware.atlassian.net/gateway/api/public/teams/v1/org/4f8ad3b0-d554-4c23-8f0b-1c57f5ee7e2a/teams/@Value(id)/members
    TRANSFER_TIMEOUT_LENGTH = 90
    UPLOAD_BODY:
      {
          "after": "@Value(endCursor)"
      }
    UPLOAD_TYPE = Specify Upload Body
    USE_COOKIES = No
    VERIFY_SSL_CERTIFICATES = Yes
    AUTH_METHOD = Web Connection
    UPLOAD_CONTENT_TYPE = JSON (application/json)
    -> JSONExtractor_5

Bookmark: Rename department and division to team_name
AttributeManager_2
    ATTR_TABLE = SET_TO team_name (varchar(200)) = @Value(department_name)
    -> DuplicateFilter
    -> FeatureMerger_2 [REQUESTOR]
    -> ListBuilder_2
AttributeManager_3
    ATTR_TABLE = SET_TO team_name (varchar(200)) = @Value(division_name)
    -> DuplicateFilter
    -> FeatureMerger_2 [REQUESTOR]
    -> ListBuilder_2

Bookmark: Get unique team names
DuplicateFilter
    INPUT_ORDERED_CHOICE_LOOKUP = NO
    KEYATTR = team_name
    PRESERVE_FEATURE_ORDER_LOOKUP = PER_OUTPUT_PORT
    INPUT_ORDERED_CHOICE = No
    UNIQUE -> Tester_2
Tester_2
    BOOL_OP = OR
    TEST_CLAUSE = TEST team_name ATTRIBUTE_HAS_A_VALUE ""
    TEST_MODE = TEST
    PASSED -> FeatureMerger [REQUESTOR]

Bookmark: Create new team
FeatureMerger
    ATTR_ACCUM_MODE = Merge Supplier
    ATTR_CONFLICT_RES_LOOKUP = REQUESTOR_IF_CONFLICT
    IGNORE_NULLS = No
    JOIN_KEYS = @Value(team_name) @Value(name) AUTO
    MERGE_TYPE = Attributes Only
    PRESERVE_FEATURE_ORDER_LOOKUP = PER_OUTPUT_PORT
    PROCESS_DUPS = NO
    REJECT_NULL_MISSING_KEYS = No
    SUPPLIERS_FIRST = No
    ATTR_CONFLICT_RES = Use Requestor
    UNMERGED_REQUESTOR -> Tester
Tester
    BOOL_OP = OR
    TEST_CLAUSE = TEST team_name ATTRIBUTE_HAS_A_VALUE ""
    TEST_MODE = TEST
    PASSED -> Tester_4
Note: Preview Mode?
Tester_4
    BOOL_OP = OR
    TEST_CLAUSE = TEST $(PREVIEW_MODE) = YES
    TEST_MODE = TEST
    PASSED -> HTTPCaller_11
    FAILED -> HTTPCaller
Note: notify techops_automation of would be Team creation
HTTPCaller_11
    CONNECTION_TIMEOUT_LENGTH = 60
    CONTENT_TYPE_LOOKUP = text/plain
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE_LOOKUP = NO
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - Atlassian Team Created (Preview Mode)",
              "text": "@Value(team_name)",
              "color": "good"
          }
          ]
      }
    UPLOAD_TYPE = Specify Upload Body
    USE_COOKIES = No
    VERIFY_SSL_CERTIFICATES = Yes
    SAVE_FILE = Attribute
    UPLOAD_CONTENT_TYPE = Text (text/plain)

Bookmark: Create new teams and add to cache db
Note: create atlassian team
HTTPCaller
    AUTH_METHOD_TYPE = NC
    AUTH_NAMED_CONNECTION = SET Atlassian Admin Header Connection
    CLIENT_CERTIFICATE_TYPE = NONE
    CONNECTION_TIMEOUT_LENGTH = 60
    CONTENT_TYPE_LOOKUP = application/json
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://safesoftware.atlassian.net/gateway/api/public/teams/v1/org/4f8ad3b0-d554-4c23-8f0b-1c57f5ee7e2a/teams/
    TRANSFER_TIMEOUT_LENGTH = 90
    UPLOAD_BODY:
      {
          "description": "Team @Value(team_name)",
          "displayName": "@Value(team_name)",
          "teamType": "MEMBER_INVITE"
      }
    UPLOAD_TYPE = Specify Upload Body
    USE_COOKIES = No
    VERIFY_SSL_CERTIFICATES = Yes
    AUTH_METHOD = Web Connection
    UPLOAD_CONTENT_TYPE = JSON (application/json)
    -> JSONExtractor
    -> HTTPCaller_5
Note: notify techops_automation of Team creation
HTTPCaller_5
    CONNECTION_TIMEOUT_LENGTH = 60
    CONTENT_TYPE_LOOKUP = text/plain
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE_LOOKUP = NO
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - Created Atlassian Team",
              "text": "@Value(team_name)",
              "color": "good"
          }
          ]
      }
    UPLOAD_TYPE = Specify Upload Body
    USE_COOKIES = No
    VERIFY_SSL_CERTIFICATES = Yes
    SAVE_FILE = Attribute
    UPLOAD_CONTENT_TYPE = Text (text/plain)
Note: extract teamId from response
JSONExtractor
    EXTRACT_QUERY_TABLE = teamId json["teamId"]
    JSON_DOCUMENT = @Value(_response_body)
    READ_FROM_FILE = NO
    EVALUATED -> SQLExecutor_2 [INITIATOR]
SQLExecutor_2
    COMBINE_ATTRS = Result Attributes Only
    COMBINE_GEOM = Initiator Geometry Only
    DATASET = IS FH SET DB
    FORMAT = POSTGRES
    OUTPUT_FEATURES = DATA_ONLY
    POSTGRES_CREATE_FEATURE_TABLES_FROM_DATA = Yes
    POSTGRES_NAMED_CONNECTION = IS FH SET DB
    POSTGRES_QUERY_FEATURE_TYPES_FOR_MERGE_FILTERS = Yes
    POSTGRES_READ_TIME_WITH_TIMEZONE = Yes
    SQL_STATEMENT:
      INSERT INTO public.atlassian_teams (id, name)
      VALUES ('@Value(teamId)', '@Value(team_name)')

Bookmark: Remove members from team
ListBuilder_2
    GROUP_BY = team_name
    LIST_ATTRS_TO_INCLUDE = Atlassian Account ID team_name
    LIST_NAME = ukg_list
    -> FeatureMerger_3 [SUPPLIER]
FeatureMerger_3
    ATTR_ACCUM_MODE = Merge Supplier
    ATTR_CONFLICT_RES_LOOKUP = REQUESTOR_IF_CONFLICT
    IGNORE_NULLS = No
    JOIN_KEYS = @Value(name) @Value(team_name) AUTO
    MERGE_TYPE = Attributes Only
    PRESERVE_FEATURE_ORDER_LOOKUP = PER_OUTPUT_PORT
    PROCESS_DUPS = NO
    REJECT_NULL_MISSING_KEYS = No
    SUPPLIERS_FIRST = No
    ATTR_CONFLICT_RES = Use Requestor
    MERGED -> ListSearcher_2
ListSearcher_2
    ATTR_VALUE = @Value(account_id)
    CASE = CASE_INSENSITIVE
    INDEX_ATTR = _list_index
    LIST_ATTR = ukg_list{}.Atlassian Account ID
    MATCHTYPE = FIRST_MATCHED_ENCODED
    PRESERVE_FEATURE_ORDER_LOOKUP = PER_OUTPUT_PORT
    NOT_FOUND -> Tester_6
Note: Preview Mode?
Tester_6
    BOOL_OP = OR
    TEST_CLAUSE = TEST $(PREVIEW_MODE) = YES
    TEST_MODE = TEST
    PASSED -> HTTPCaller_8
    FAILED -> HTTPCaller_4
Note: notify techops_automation of would be member removal
HTTPCaller_8
    CONNECTION_TIMEOUT_LENGTH = 60
    CONTENT_TYPE_LOOKUP = text/plain
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE_LOOKUP = NO
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - Removed user from Atlassian Team (Preview Mode)",
              "text": "@Value(first) @Value(last) from @Value(name)",
              "color": "good"
          }
          ]
      }
    UPLOAD_TYPE = Specify Upload Body
    USE_COOKIES = No
    VERIFY_SSL_CERTIFICATES = Yes
    SAVE_FILE = Attribute
    UPLOAD_CONTENT_TYPE = Text (text/plain)
Note: Remove member from team
HTTPCaller_4
    AUTH_METHOD_TYPE = NC
    AUTH_NAMED_CONNECTION = SET Atlassian Admin Header Connection
    CLIENT_CERTIFICATE_TYPE = NONE
    CONNECTION_TIMEOUT_LENGTH = 60
    CONTENT_TYPE_LOOKUP = application/json
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://safesoftware.atlassian.net/gateway/api/public/teams/v1/org/4f8ad3b0-d554-4c23-8f0b-1c57f5ee7e2a/teams/@Value(id)/members/remove
    TRANSFER_TIMEOUT_LENGTH = 90
    UPLOAD_BODY:
      {
          "members": [
              {
                  "accountId": "@Value(account_id)"
              }
          ]
      }
    UPLOAD_TYPE = Specify Upload Body
    USE_COOKIES = No
    VERIFY_SSL_CERTIFICATES = Yes
    AUTH_METHOD = Web Connection
    UPLOAD_CONTENT_TYPE = JSON (application/json)
    -> HTTPCaller_9
Note: notify techops_automation of member removal
HTTPCaller_9
    CONNECTION_TIMEOUT_LENGTH = 60
    CONTENT_TYPE_LOOKUP = text/plain
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE_LOOKUP = NO
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - Removed user from Atlassian Team",
              "text": "@Value(first) @Value(last) from @Value(name)",
              "color": "good"
          }
          ]
      }
    UPLOAD_TYPE = Specify Upload Body
    USE_COOKIES = No
    VERIFY_SSL_CERTIFICATES = Yes
    SAVE_FILE = Attribute
    UPLOAD_CONTENT_TYPE = Text (text/plain)

Bookmark: Add members to team
Note: Create a list of accountIds in each team
ListBuilder
    GROUP_BY = name id
    LIST_ATTRS_TO_INCLUDE = account_id
    LIST_NAME = _list
    -> FeatureMerger_2 [SUPPLIER]
FeatureMerger_2
    ATTR_ACCUM_MODE = Merge Supplier
    ATTR_CONFLICT_RES_LOOKUP = REQUESTOR_IF_CONFLICT
    IGNORE_NULLS = No
    JOIN_KEYS = @Value(team_name) @Value(name) AUTO
    MERGE_TYPE = Attributes Only
    PRESERVE_FEATURE_ORDER_LOOKUP = PER_OUTPUT_PORT
    PROCESS_DUPS = NO
    REJECT_NULL_MISSING_KEYS = No
    SUPPLIERS_FIRST = No
    ATTR_CONFLICT_RES = Use Requestor
    MERGED -> ListSearcher
Note: search for members to add
ListSearcher
    ATTR_VALUE = @Value(Atlassian Account ID)
    CASE = CASE_INSENSITIVE
    INDEX_ATTR = _list_index
    LIST_ATTR = _list{}.account_id
    MATCHTYPE = FIRST_MATCHED_ENCODED
    PRESERVE_FEATURE_ORDER_LOOKUP = PER_OUTPUT_PORT
    NOT_FOUND -> Tester_5
Note: Preview Mode?
Tester_5
    BOOL_OP = OR
    TEST_CLAUSE = TEST $(PREVIEW_MODE) = YES
    TEST_MODE = TEST
    PASSED -> HTTPCaller_6
    FAILED -> HTTPCaller_3
Note: notify techops_automation of would be member addition
HTTPCaller_6
    CONNECTION_TIMEOUT_LENGTH = 60
    CONTENT_TYPE_LOOKUP = text/plain
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE_LOOKUP = NO
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - Added user to Atlassian Team (Preview Mode)",
              "text": "@Value(first) @Value(last) to @Value(name)",
              "color": "good"
          }
          ]
      }
    UPLOAD_TYPE = Specify Upload Body
    USE_COOKIES = No
    VERIFY_SSL_CERTIFICATES = Yes
    SAVE_FILE = Attribute
    UPLOAD_CONTENT_TYPE = Text (text/plain)
Note: Add member to team
HTTPCaller_3
    AUTH_METHOD_TYPE = NC
    AUTH_NAMED_CONNECTION = SET Atlassian Admin Header Connection
    CLIENT_CERTIFICATE_TYPE = NONE
    CONNECTION_TIMEOUT_LENGTH = 60
    CONTENT_TYPE_LOOKUP = application/json
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://safesoftware.atlassian.net/gateway/api/public/teams/v1/org/4f8ad3b0-d554-4c23-8f0b-1c57f5ee7e2a/teams/@Value(id)/members/add
    TRANSFER_TIMEOUT_LENGTH = 90
    UPLOAD_BODY:
      {
          "members": [
              {
                  "accountId": "@Value(Atlassian Account ID)"
              }
          ]
      }
    UPLOAD_TYPE = Specify Upload Body
    USE_COOKIES = No
    VERIFY_SSL_CERTIFICATES = Yes
    AUTH_METHOD = Web Connection
    UPLOAD_CONTENT_TYPE = JSON (application/json)
    -> HTTPCaller_7
Note: notify techops_automation of member addition
HTTPCaller_7
    CONNECTION_TIMEOUT_LENGTH = 60
    CONTENT_TYPE_LOOKUP = text/plain
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE_LOOKUP = NO
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - Added user to Atlassian Team",
              "text": "@Value(first) @Value(last) to @Value(name)",
              "color": "good"
          }
          ]
      }
    UPLOAD_TYPE = Specify Upload Body
    USE_COOKIES = No
    VERIFY_SSL_CERTIFICATES = Yes
    SAVE_FILE = Attribute
    UPLOAD_CONTENT_TYPE = Text (text/plain)

FME custom transformer AtlassianIDGetter

Parameters:
- EMAIL = @Value(email)   # email

email (input)
    -> HTTPCaller_8
Note: get accountId
HTTPCaller_8
    AUTH_METHOD_TYPE = NC
    AUTH_NAMED_CONNECTION = SET Atlassian Admin Header Connection
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    REDIRECT_AUTH = ORIGINAL_DOMAIN_ONLY
    SAVE_FILE_LOOKUP = NO
    STATUS_CODE_ATTR = _http_status_code
    TARGET_ATTR = _user_response_body
    TARGET_ATTR_ENCODING = auto-detect
    TARGET_URL = https://safesoftware.atlassian.net/rest/api/3/user/search?query=@Value(email)
    TRANSFER_TIMEOUT_LENGTH = 90
    USE_COOKIES = No
    VERIFY_SSL_CERTIFICATES = Yes
    AUTH_METHOD = Web Connection
    SAVE_FILE = Attribute
    -> JSONExtractor
Note: extract accountId
JSONExtractor
    EXTRACT_QUERY_TABLE = "Atlassian Account ID" json[*]["accountId"]
    JSON_DOCUMENT = @Value(_user_response_body)
    READ_FROM_FILE = NO
    EVALUATED -> output (output)
output (output)

FME custom transformer SafeEmployeeReader

Note: Gets employee information / Author: Ellaine Chan
Creator
    GEOMTYPE = Geometry Object
    NUM = 1
    CREATED -> HTTPCaller
Note: Get user list
HTTPCaller
    AUTH_METHOD_TYPE = NC
    AUTH_NAMED_CONNECTION = services.api.safe.com prod connection
    CLIENT_CERTIFICATE_TYPE = NONE
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://services.api.safe.com/v1/users/list
    TRANSFER_TIMEOUT_LENGTH = 90
    USE_COOKIES = No
    VERIFY_SSL_CERTIFICATES = Yes
    AUTH_METHOD = Web Connection
    -> JSONFragmenter
JSONFragmenter
    EXPLODE_FORMAT = JSON
    EXTRACT_ATTR = No
    JSON_ATTR = _response_body
    JSON_QUERY = json[*]
    READ_FROM_FILE = NO
    REJECT_EMPTY_LISTS = YES
    FRAGMENTS -> JSONExtractor_6
JSONExtractor_6
    EXTRACT_QUERY_TABLE = email json["email"] first json["first"] last json["last"]
    JSON_DOCUMENT = @Value(_response_body)
    READ_FROM_FILE = NO
    EVALUATED -> AttributeManager_4
Note: add @safe.com to email
AttributeManager_4
    ATTR_TABLE = SET_TO email = @Value(email)@safe.com
    -> HTTPCaller_19
Note: Get user info
HTTPCaller_19
    AUTH_METHOD_TYPE = NC
    AUTH_NAMED_CONNECTION = SET Atlassian Admin Header Connection
    CLIENT_CERTIFICATE_TYPE = NONE
    CONNECTION_TIMEOUT_LENGTH = 60
    CONTENT_TYPE_LOOKUP = application/json
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://ax713gk4xl.execute-api.us-west-2.amazonaws.com/prod/user_team_info
    TRANSFER_TIMEOUT_LENGTH = 90
    UPLOAD_BODY:
      {
      "email": "@Value(email)"
      }
    UPLOAD_TYPE = Specify Upload Body
    USE_COOKIES = No
    VERIFY_SSL_CERTIFICATES = Yes
    AUTH_METHOD = Web Connection
    UPLOAD_CONTENT_TYPE = JSON (application/json)
    -> JSONExtractor_7
Note: extract fields
JSONExtractor_7
    EXTRACT_QUERY_TABLE = team_name json["data"]["team"]["hierarchy"]["team"]["name"] team_lead_email json["data"]["team"]["hierarchy"]["team"]["lead"]["email"] team_alt_name json["data"]["team"]["hierarchy"]["team"]["alt_name"] department_name json["data"]["team"]["hierarchy"]["department"]["name"] department_lead_email json["data"]["team"]["hierarchy"]["department"]["lead"]["email"] division_name json["data"]["team"]["hierarchy"]["division"]["name"] division_lead_email json["data"]["team"]["hierarchy"]["division"]["lead"]["email"]
    JSON_DOCUMENT = @Value(_response_body)
    READ_FROM_FILE = NO
    EVALUATED -> Tester
Note: if team has alt_name
Tester
    BOOL_OP = OR
    TEST_CLAUSE = TEST team_alt_name ATTRIBUTE_HAS_A_VALUE ""
    TEST_MODE = TEST
    PASSED -> AttributeManager
    FAILED -> AttributeKeeper_2
Note: assign alt_name as team_name
AttributeManager
    ATTR_TABLE = SET_TO team_name (varchar(200)) = @Value(team_alt_name)
    -> AttributeKeeper_2
AttributeKeeper_2
    CREATE_BULK_MODE_FEATURES = NO
    KEEP_ATTRS = department_lead_email,department_name,division_lead_email,division_name,email,first,last,team_lead_email,team_name
    -> Output (output)
Output (output)
