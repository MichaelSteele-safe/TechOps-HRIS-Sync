FME workspace HR - UKG to Jira Groups Sync.fmw

Parameters:
- SLACK_NOTIFICATION_WEBHOOK = https://hooks.slack.com/services/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   # webhook to send notification to slack

Writers:
- CSV2_1: CSV2 to /Users/ellaine.chan/Desktop

Note: UKG Generated reports are sent to hrisautomation@safe.com, picked up by Google App Scripts and dropped to Google Drive. This workspace reads the latest CSV files to migrate data into our database. / Author: Ellaine Chan
SafeEmployeeReader
    -> AttributeCreator_12
AtlassianIDGetter
    EMAIL = @Value(email)
    -> Tester

Bookmark: Determine Team Leads
Note: create team_lead fields
AttributeCreator_12
    ATTR_TABLE:
      SET_TO team_lead = 0
      SET_TO marketing_team_lead = 0
      SET_TO information_services_team_lead = 0
      SET_TO dev_team_lead = 0
    -> TestFilter_2
TestFilter_2
    DEFAULT_VALUE = <UNFILTERED>
    PASSED_TEST_GROUP_OUTPUT = FIRST
    TEST_LIST = "BOOL_OP,OR,COMPOSITE_TEST,""""""1"""""",TEST_CLAUSE,TEST @Value(email) = @Value(team_lead_email)",is-team-lead,"BOOL_OP,OR,COMPOSITE_TEST,""""""1"""""",TEST_CLAUSE,TEST @Value(email) = @Value(department_lead_email)",is-department-lead,"BOOL_OP,OR,COMPOSITE_TEST,""""""1"""""",TEST_CLAUSE,TEST @Value(email) = @Value(division_lead_email)",is-division-lead
    is-team-lead -> AttributeManager_5
    is-department-lead -> AttributeManager_5
    is-division-lead -> AttributeManager_5
    <UNFILTERED> -> AtlassianIDGetter [email]
Note: set team_lead = 1
AttributeManager_5
    ATTR_TABLE = SET_TO team_lead = 1
    -> TestFilter_3
TestFilter_3
    DEFAULT_VALUE = <UNFILTERED>
    PASSED_TEST_GROUP_OUTPUT = FIRST
    TEST_LIST = "BOOL_OP,OR,COMPOSITE_TEST,""""""1"""""",TEST_CLAUSE,CASE_INSENSITIVE_TEST @Value(division_name) CONTAINS Marketing",Marketing,"BOOL_OP,OR,COMPOSITE_TEST,""""""1"""""",TEST_CLAUSE,CASE_INSENSITIVE_TEST @Value(division_name) CONTAINS Information Services",IS,"BOOL_OP,OR,COMPOSITE_TEST,""""""1"""""",TEST_CLAUSE,CASE_INSENSITIVE_TEST @Value(division_name) CONTAINS Product Development",Product Development
    Marketing -> AttributeManager_6
    IS -> AttributeManager_7
    Product Development -> AttributeManager_2
    <UNFILTERED> -> AtlassianIDGetter [email]
Note: set marketing lead
AttributeManager_6
    ATTR_TABLE = SET_TO marketing_team_lead = 1
    -> AtlassianIDGetter [email]
Note: set IS lead
AttributeManager_7
    ATTR_TABLE = SET_TO information_services_team_lead = 1
    -> AtlassianIDGetter [email]
Note: set dev lead
AttributeManager_2
    ATTR_TABLE:
      SET_TO information_services_team_lead
      SET_TO dev_team_lead = 1
    -> AtlassianIDGetter [email]

Bookmark: Update Jira Groups
Tester
    BOOL_OP = OR
    TEST_CLAUSE = TEST Atlassian Account ID ATTRIBUTE_HAS_A_VALUE ""
    TEST_MODE = TEST
    PASSED -> HTTPCaller_9
Note: get groups that user is in
HTTPCaller_9
    AUTH_METHOD = Web Connection
    AUTH_NAMED_CONNECTION = SET Atlassian Admin Header Connection
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _user_group_response_body
    TARGET_ATTR_ENCODING = auto-detect
    TARGET_URL = https://safesoftware.atlassian.net/rest/api/3/user?accountId=@Value(Atlassian Account ID)&expand=groups
    TRANSFER_TIMEOUT_LENGTH = 90
    USE_COOKIES = No
    VERIFY_SSL_CERTIFICATES = Yes
    -> AttributeCreator_4
AttributeCreator_4
    ATTR_TABLE:
      SET_TO group_operation
      SET_TO jira_group
    -> PythonCaller
    -> PythonCaller_5
    -> PythonCaller_2
    -> PythonCaller_3
    -> PythonCaller_4
    -> PythonCaller_6
    -> PythonCaller_8
    -> PythonCaller_9
    -> PythonCaller_7
Note: Maintain group jira-plans-viewers (ADD ONLY)
PythonCaller_8
    PYTHONSOURCE:
      import fme
      import fmeobjects
      import json


      class FeatureProcessor(object):

          def __init__(self):
              """Base constructor for class members."""
              pass

          def input(self, feature):
              group_name = "jira-plans-viewers"
              user_groups_list = json.loads(feature.getAttribute('_user_group_response_body'))["groups"]["items"]
              user_group_name_list = {group["name"] for group in user_groups_list}
              groups_to_include = ["team-product-development", "team-information-services", "group-teamleads", "group-executive"]
              in_group = any(name in groups_to_include for name in user_group_name_list)
              print(user_group_name_list)

              if in_group and group_name not in user_group_name_list:
                  new_feature = feature.clone()
                  new_feature.setAttribute('group_operation', 'add')
                  new_feature.setAttribute('jira_group', group_name)
                  self.pyoutput(new_feature)

          def close(self):
              """This method is called once all the FME Features have been processed
              from input().
              """
              pass

          def process_group(self):

              pass
    PYTHONSYMBOL = FeatureProcessor
    -> HTTPCaller_13
Note: Maintain group jira-plans-creators (ADD ONLY)
PythonCaller_7
    PYTHONSOURCE:
      import fme
      import fmeobjects
      import json


      class FeatureProcessor(object):

          def __init__(self):
              """Base constructor for class members."""
              pass

          def input(self, feature):
              group_name = "jira-plans-creators"
              user_groups_list = json.loads(feature.getAttribute('_user_group_response_body'))["groups"]["items"]
              user_group_name_list = {group["name"] for group in user_groups_list}
              groups_to_include = ["group-devleads", "team-product-management", "group-technical-directors", "group-founders", "group-infosrvcs-leads"]
              in_group = any(name in groups_to_include for name in user_group_name_list)
              print(user_group_name_list)

              if in_group and group_name not in user_group_name_list:
                  new_feature = feature.clone()
                  new_feature.setAttribute('group_operation', 'add')
                  new_feature.setAttribute('jira_group', group_name)
                  self.pyoutput(new_feature)

          def close(self):
              """This method is called once all the FME Features have been processed
              from input().
              """
              pass

          def process_group(self):

              pass
    PYTHONSYMBOL = FeatureProcessor
    -> HTTPCaller_13
Note: Maintain group-devleads
PythonCaller_9
    PYTHONSOURCE:
      import fme
      import fmeobjects
      import json


      class FeatureProcessor(object):
          """Template Class Interface:
          When using this class, make sure its name is set as the value of the 'Class
          to Process Features' transformer parameter.
          """

          def __init__(self):
              """Base constructor for class members."""
              pass

          def input(self, feature):
              user_group_name_list = []
              group_name = "group-devleads"
              user_groups_list = json.loads(feature.getAttribute('_user_group_response_body'))["groups"]["items"]
              in_group = False
              if feature.getAttribute('dev_team_lead') == 1:
                  in_group = True
              for group in user_groups_list:
                  user_group_name_list.append(group["name"])
                  if in_group == False and group["name"] == group_name:
                      new_feature = feature.clone()
                      new_feature.setAttribute('group_operation', 'delete')
                      new_feature.setAttribute('jira_group', group_name)
                      self.pyoutput(new_feature)
              if in_group and group_name not in user_group_name_list:
                  new_feature = feature.clone()
                  new_feature.setAttribute('group_operation', 'add')
                  new_feature.setAttribute('jira_group', group_name)
                  self.pyoutput(new_feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> HTTPCaller_13
Note: Maintain group-qa
PythonCaller_6
    PYTHONSOURCE:
      import fme
      import fmeobjects
      import json


      class FeatureProcessor(object):
          """Template Class Interface:
          When using this class, make sure its name is set as the value of the 'Class
          to Process Features' transformer parameter.
          """

          def __init__(self):
              """Base constructor for class members."""
              pass

          def input(self, feature):
              user_group_name_list = []
              group_name = "group-quality"
              user_groups_list = json.loads(feature.getAttribute('_user_group_response_body'))["groups"]["items"]
              in_group = False
              if "quality" in feature.getAttribute('title').lower() or "QA" in feature.getAttribute('title') or "Test " in feature.getAttribute('title'):
                  in_group = True
              for group in user_groups_list:
                  user_group_name_list.append(group["name"])
                  if in_group == False and group["name"] == group_name:
                      new_feature = feature.clone()
                      new_feature.setAttribute('group_operation', 'delete')
                      new_feature.setAttribute('jira_group', group_name)
                      self.pyoutput(new_feature)
              if in_group and group_name not in user_group_name_list:
                  new_feature = feature.clone()
                  new_feature.setAttribute('group_operation', 'add')
                  new_feature.setAttribute('jira_group', group_name)
                  self.pyoutput(new_feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> HTTPCaller_13
Note: Maintain group-customer-support
PythonCaller_5
    PYTHONSOURCE:
      import fme
      import fmeobjects
      import json


      class FeatureProcessor(object):
          """Template Class Interface:
          When using this class, make sure its name is set as the value of the 'Class
          to Process Features' transformer parameter.
          """

          def __init__(self):
              """Base constructor for class members."""
              pass

          def input(self, feature):
              user_group_name_list = []
              customer_success_group = "group-customer-support"
              user_groups_list = json.loads(feature.getAttribute('_user_group_response_body'))["groups"]["items"]
              in_customer_success_group = False
              if feature.getAttribute('department_name') == "Customer Knowledge" and feature.getAttribute('team_name') != "Customer Education" and feature.getAttribute('team_name') != "Customer Knowledge":
                  in_customer_success_group = True
              for group in user_groups_list:
                  user_group_name_list.append(group["name"])
                  if in_customer_success_group == False and group["name"] == customer_success_group:
                      new_feature = feature.clone()
                      new_feature.setAttribute('group_operation', 'delete')
                      new_feature.setAttribute('jira_group', customer_success_group)
                      self.pyoutput(new_feature)
              if in_customer_success_group and customer_success_group not in user_group_name_list:
                  new_feature = feature.clone()
                  new_feature.setAttribute('group_operation', 'add')
                  new_feature.setAttribute('jira_group', customer_success_group)
                  self.pyoutput(new_feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> HTTPCaller_13
Note: Maintain group-team-lead
PythonCaller_2
    PYTHONSOURCE:
      import fme
      import fmeobjects
      import json


      class FeatureProcessor(object):
          """Template Class Interface:
          When using this class, make sure its name is set as the value of the 'Class
          to Process Features' transformer parameter.
          """

          def __init__(self):
              """Base constructor for class members."""
              pass

          def input(self, feature):
              user_group_name_list = []
              teamlead_group = "group-teamleads"
              user_groups_list = json.loads(feature.getAttribute('_user_group_response_body'))["groups"]["items"]
              in_team_lead_group = False
              if feature.getAttribute('team_lead') == 1:
                  in_team_lead_group = True
              for group in user_groups_list:
                  user_group_name_list.append(group["name"])
                  if in_team_lead_group == False and group["name"] == teamlead_group:
                      new_feature = feature.clone()
                      new_feature.setAttribute('group_operation', 'delete')
                      new_feature.setAttribute('jira_group', teamlead_group)
                      self.pyoutput(new_feature)
              if in_team_lead_group and teamlead_group not in user_group_name_list:
                  new_feature = feature.clone()
                  new_feature.setAttribute('group_operation', 'add')
                  new_feature.setAttribute('jira_group', teamlead_group)
                  self.pyoutput(new_feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> HTTPCaller_13
Note: Maintain group-infosrvcs-leads
PythonCaller_3
    PYTHONSOURCE:
      import fme
      import fmeobjects
      import json


      class FeatureProcessor(object):
          """Template Class Interface:
          When using this class, make sure its name is set as the value of the 'Class
          to Process Features' transformer parameter.
          """

          def __init__(self):
              """Base constructor for class members."""
              pass

          def input(self, feature):
              user_group_name_list = []
              teamlead_group = "group-infosrvcs-leads"
              user_groups_list = json.loads(feature.getAttribute('_user_group_response_body'))["groups"]["items"]
              in_team_lead_group = False
              if feature.getAttribute('information_services_team_lead') == 1:
                  in_team_lead_group = True
              for group in user_groups_list:
                  user_group_name_list.append(group["name"])
                  if in_team_lead_group == False and group["name"] == teamlead_group:
                      new_feature = feature.clone()
                      new_feature.setAttribute('group_operation', 'delete')
                      new_feature.setAttribute('jira_group', teamlead_group)
                      self.pyoutput(new_feature)
              if in_team_lead_group and teamlead_group not in user_group_name_list:
                  new_feature = feature.clone()
                  new_feature.setAttribute('group_operation', 'add')
                  new_feature.setAttribute('jira_group', teamlead_group)
                  self.pyoutput(new_feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> HTTPCaller_13
Note: Maintain group-marketing-leads
PythonCaller_4
    PYTHONSOURCE:
      import fme
      import fmeobjects
      import json


      class FeatureProcessor(object):
          """Template Class Interface:
          When using this class, make sure its name is set as the value of the 'Class
          to Process Features' transformer parameter.
          """

          def __init__(self):
              """Base constructor for class members."""
              pass

          def input(self, feature):
              user_group_name_list = []
              teamlead_group = "group-marketing-leads"
              user_groups_list = json.loads(feature.getAttribute('_user_group_response_body'))["groups"]["items"]
              in_team_lead_group = False
              if feature.getAttribute('marketing_team_lead') == 1:
                  in_team_lead_group = True
              for group in user_groups_list:
                  user_group_name_list.append(group["name"])
                  if in_team_lead_group == False and group["name"] == teamlead_group:
                      new_feature = feature.clone()
                      new_feature.setAttribute('group_operation', 'delete')
                      new_feature.setAttribute('jira_group', teamlead_group)
                      self.pyoutput(new_feature)
              if in_team_lead_group and teamlead_group not in user_group_name_list:
                  new_feature = feature.clone()
                  new_feature.setAttribute('group_operation', 'add')
                  new_feature.setAttribute('jira_group', teamlead_group)
                  self.pyoutput(new_feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> HTTPCaller_13
Note: Determine which groups user needs to be added or removed from and output as new feature
PythonCaller
    PYTHONSOURCE:
      import fme
      import fmeobjects
      import json


      class FeatureProcessor(object):
          """Template Class Interface:
          When using this class, make sure its name is set as the value of the 'Class
          to Process Features' transformer parameter.
          """

          def __init__(self):
              """Base constructor for class members."""
              pass


          def input(self, feature):
              user_groups_list = json.loads(feature.getAttribute('_user_group_response_body'))["groups"]["items"]
              user_group_name_list = []
              org3_jira_name = ""
              org2_jira_name = "team-" + feature.getAttribute('department_name').replace("- ", "" ).replace(" ", "-" ).lower()
              org1_jira_name = "team-" + feature.getAttribute('division_name').replace("- ", "" ).replace(" ", "-" ).lower()
              if feature.getAttribute('team_alt_name') == None or len(feature.getAttribute('team_alt_name')) == 0:
                  org3_jira_name =  "team-" + feature.getAttribute('team_name').replace("- ", "" ).replace(" ", "-" ).lower()
              else:
                  org3_jira_name =  "team-" + feature.getAttribute('team_alt_name').replace("- ", "" ).replace(" ", "-" ).lower()
              print(feature.getAttribute('first'))
              print(org3_jira_name)
              print(org2_jira_name)
              print(org1_jira_name)
              for group in user_groups_list:
                  print("group: %s" % group["name"])
                  user_group_name_list.append(group["name"])
                  # don't remove PMs from their dev team
                  org3_name =  feature.getAttribute('team_name').replace("Product Mgmt", "Product Management")
                  if group["name"] != org1_jira_name and group["name"] != org2_jira_name and group["name"] != org3_jira_name and group["name"].find("team") ==0:
                      if "Product Management" in org3_name:
                          dev_team = org3_name.replace("Product Management", "").rstrip().lower()
                          if dev_team not in group["name"]:
                              new_feature = feature.clone()
                              new_feature.setAttribute('group_operation', 'delete')
                              new_feature.setAttribute('jira_group', group["name"])
                              self.pyoutput(new_feature)
                      else:
                          new_feature = feature.clone()
                          new_feature.setAttribute('group_operation', 'delete')
                          new_feature.setAttribute('jira_group', group["name"])
                          self.pyoutput(new_feature)
              if not org1_jira_name in user_group_name_list:
                  new_feature = feature.clone()
                  new_feature.setAttribute('group_operation', 'add')
                  new_feature.setAttribute('jira_group', org1_jira_name)
                  self.pyoutput(new_feature)
              if not org2_jira_name in user_group_name_list:
                  new_feature = feature.clone()
                  new_feature.setAttribute('group_operation', 'add')
                  new_feature.setAttribute('jira_group', org2_jira_name)
                  self.pyoutput(new_feature)
              if not org3_jira_name in user_group_name_list:
                  if len(feature.getAttribute('team_name')) > 1:
                      new_feature = feature.clone()
                      new_feature.setAttribute('group_operation', 'add')
                      new_feature.setAttribute('jira_group', org3_jira_name)
                      self.pyoutput(new_feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> HTTPCaller_13
Note: get groupId
HTTPCaller_13
    AUTH_METHOD = Web Connection
    AUTH_NAMED_CONNECTION = SET Atlassian Admin Header Connection
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _jira_group_response_body
    TARGET_ATTR_ENCODING = auto-detect
    TARGET_URL = https://safesoftware.atlassian.net/rest/api/3/groups/picker?query=@Value(jira_group)
    TRANSFER_TIMEOUT_LENGTH = 90
    USE_COOKIES = No
    VERIFY_SSL_CERTIFICATES = Yes
    -> JSONExtractor_2
Note: extract groupId
JSONExtractor_2
    EXTRACT_QUERY_TABLE = groupId json["groups"][0]["groupId"] groupName json["groups"][0]["name"]
    JSON_DOCUMENT = @Value(_jira_group_response_body)
    READ_FROM_FILE = NO
    EVALUATED -> Tester_10
Tester_10
    BOOL_OP = OR
    TEST_CLAUSE = TEST @Value(group_operation) = add
    TEST_MODE = TEST
    PASSED -> Tester_15
    FAILED -> Tester_13
Note: does group already exist?
Tester_15
    BOOL_OP = COMPOSITE
    COMPOSITE_TEST = 1 AND 2
    TEST_CLAUSE:
      TEST groupId ATTRIBUTE_HAS_A_VALUE ""
      TEST @Value(groupName) = @Value(jira_group)
    TEST_MODE = TEST
    PASSED -> AttributeCreator_11
    FAILED -> DuplicateFilter_2
DuplicateFilter_2
    INPUT_ORDERED_CHOICE = No
    KEYATTR = jira_group
    UNIQUE -> HTTPCaller_14
    DUPLICATE -> FeatureJoiner [RIGHT]
Note: create jira group
HTTPCaller_14
    AUTH_METHOD = Web Connection
    AUTH_NAMED_CONNECTION = SET Atlassian Admin Header Connection
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _new_group_response_body
    TARGET_ATTR_ENCODING = auto-detect
    TARGET_URL = https://safesoftware.atlassian.net/rest/api/3/group
    TRANSFER_TIMEOUT_LENGTH = 90
    UPLOAD_BODY:
      {
          "name": "@Value(jira_group)"
      }
    UPLOAD_CONTENT_TYPE = JSON (application/json)
    UPLOAD_TYPE = Specify Upload Body
    USE_COOKIES = No
    VERIFY_SSL_CERTIFICATES = Yes
    -> JSONExtractor_3
Note: extract groupId
JSONExtractor_3
    EXTRACT_QUERY_TABLE = groupId json["groupId"]
    JSON_DOCUMENT = @Value(_new_group_response_body)
    READ_FROM_FILE = NO
    EVALUATED -> HTTPCaller_11
    EVALUATED -> AttributeCreator_11
    EVALUATED -> AttributeKeeper
    <REJECTED> -> HTTPCaller_4
Note: notify techops_automation jira group was created
HTTPCaller_11
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - Created Jira Group",
              "text": "@Value(jira_group)",
              "color": "good"
          }
          ]
      }
    UPLOAD_CONTENT_TYPE = Text (text/plain)
    UPLOAD_TYPE = Specify Upload Body
    USE_COOKIES = No
    VERIFY_SSL_CERTIFICATES = Yes
Note: notify techops_automation of error
HTTPCaller_4
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - Error",
              "text": "Could not create jira group @Value(jira_group)",
              "color": "danger"
          }
          ]
      }
    UPLOAD_CONTENT_TYPE = Text (text/plain)
    UPLOAD_TYPE = Specify Upload Body
    USE_COOKIES = No
    VERIFY_SSL_CERTIFICATES = Yes
AttributeKeeper
    CREATE_BULK_MODE_FEATURES = NO
    KEEP_ATTRS = groupId,jira_group
    -> FeatureJoiner [LEFT]
FeatureJoiner
    ATTR_CONFLICT_RES = Prefer Left
    GEOMETRY_HANDLING = Prefer Left
    JOIN_KEYS = jira_group jira_group AUTO
    JOIN_MODE = Left
    JOINED -> AttributeCreator_11
AttributeCreator_11
    ATTR_TABLE:
      SET_TO add_url = https://safesoftware.atlassian.net/rest/api/3/group/user?groupId=@Value(groupId)
      SET_TO url_body = {
            "accountId": "@Value(Atlassian Account ID)"
        }
    -> HTTPCaller_16
Note: add user to jira group
HTTPCaller_16
    AUTH_METHOD = Web Connection
    AUTH_NAMED_CONNECTION = SET Atlassian Admin Header Connection
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _new_group_response_body
    TARGET_ATTR_ENCODING = auto-detect
    TARGET_URL = https://safesoftware.atlassian.net/rest/api/3/group/user?groupId=@Value(groupId)
    TRANSFER_TIMEOUT_LENGTH = 90
    UPLOAD_BODY:
      {
          "accountId": "@Value(Atlassian Account ID)"
      }
    UPLOAD_CONTENT_TYPE = JSON (application/json)
    UPLOAD_TYPE = Specify Upload Body
    USE_COOKIES = No
    VERIFY_SSL_CERTIFICATES = Yes
    -> HTTPCaller_12
    <REJECTED> -> HTTPCaller_3
Note: notify techops_automation user was added to group
HTTPCaller_12
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - User added to Jira Group",
              "text": "Employee @Value(first) @Value(last) was added to @Value(jira_group)",
              "color": "good"
          }
          ]
      }
    UPLOAD_CONTENT_TYPE = Text (text/plain)
    UPLOAD_TYPE = Specify Upload Body
    USE_COOKIES = No
    VERIFY_SSL_CERTIFICATES = Yes
Note: notify techops_automation of error
HTTPCaller_3
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS -  Error",
              "text": "Employee @Value(first) @Value(last) could not be added to group @Value(jira_group)",
              "color": "danger"
          }
          ]
      }
    UPLOAD_CONTENT_TYPE = Text (text/plain)
    UPLOAD_TYPE = Specify Upload Body
    USE_COOKIES = No
    VERIFY_SSL_CERTIFICATES = Yes
Note: EXCEPTIONS
Tester_13
    BOOL_OP = OR
    TEST_CLAUSE:
      TEST @Value(jira_group) = team-facilities
      CASE_INSENSITIVE_TEST john.leesbonnie.alexander CONTAINS @Value(email)
    TEST_MODE = PER_TEST
    FAILED -> AttributeCreator_10
AttributeCreator_10
    ATTR_TABLE = SET_TO delete_url = https://safesoftware.atlassian.net/rest/api/3/group/user?groupId=@Value(groupId)&accountId=@Value(Atlassian Account ID)
    -> HTTPCaller_18
Note: remove user from group
HTTPCaller_18
    AUTH_METHOD = Web Connection
    AUTH_NAMED_CONNECTION = SET Atlassian Admin Header Connection
    CONNECTION_TIMEOUT_LENGTH = 60
    ERROR_ATTR = _error
    FOLLOW_REDIRECTS = FOLLOW_WITH_GET
    HTTP_METHOD = DELETE
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _remove_user_from_group_response_body
    TARGET_ATTR_ENCODING = auto-detect
    TARGET_URL = https://safesoftware.atlassian.net/rest/api/3/group/user?groupId=@Value(groupId)&accountId=@Value(Atlassian Account ID)
    TRANSFER_TIMEOUT_LENGTH = 90
    UPLOAD_BODY:
      {
          "accountId": "@Value(Atlassian Account ID)"
      }
    UPLOAD_CONTENT_TYPE = JSON (application/json)
    UPLOAD_TYPE = Specify Upload Body
    USE_COOKIES = No
    VERIFY_SSL_CERTIFICATES = Yes
    -> HTTPCaller_10
    <REJECTED> -> HTTPCaller_2
Note: notify techops_automation of removed from jira group
HTTPCaller_10
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - User removed from Jira Group",
              "text": "Employee @Value(first) @Value(last) was removed from group @Value(jira_group)",
              "color": "danger"
          }
          ]
      }
    UPLOAD_CONTENT_TYPE = Text (text/plain)
    UPLOAD_TYPE = Specify Upload Body
    USE_COOKIES = No
    VERIFY_SSL_CERTIFICATES = Yes
Note: notify techops_automation of error
HTTPCaller_2
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS -  Error",
              "text": "Employee @Value(first) @Value(last) could not be removed from group @Value(jira_group)",
              "color": "danger"
          }
          ]
      }
    UPLOAD_CONTENT_TYPE = Text (text/plain)
    UPLOAD_TYPE = Specify Upload Body
    USE_COOKIES = No
    VERIFY_SSL_CERTIFICATES = Yes

FME custom transformer SafeEmployeeReader

Note: Gets employee information / Author: Ellaine Chan
Creator
    GEOMTYPE = Geometry Object
    NUM = 1
    CREATED -> HTTPCaller
Note: Get user list
HTTPCaller
    AUTH_METHOD = Web Connection
    AUTH_NAMED_CONNECTION = services.api.safe.com prod connection
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://services.api.safe.com/v1/users/list
    TRANSFER_TIMEOUT_LENGTH = 90
    USE_COOKIES = No
    VERIFY_SSL_CERTIFICATES = Yes
    -> JSONFragmenter
JSONFragmenter
    EXPLODE_FORMAT = JSON
    EXTRACT_ATTR = No
    JSON_ATTR = _response_body
    JSON_QUERY = json[*]
    READ_FROM_FILE = NO
    REJECT_EMPTY_LISTS = YES
    FRAGMENTS -> JSONExtractor_6
JSONExtractor_6
    EXTRACT_QUERY_TABLE = email json["email"] first json["first"] last json["last"] title json["title"]
    JSON_DOCUMENT = @Value(_response_body)
    READ_FROM_FILE = NO
    EVALUATED -> AttributeManager_4
Note: add @safe.com to email
AttributeManager_4
    ATTR_TABLE = SET_TO email = @Value(email)@safe.com
    -> HTTPCaller_19
Note: Get user info
HTTPCaller_19
    AUTH_METHOD = Web Connection
    AUTH_NAMED_CONNECTION = SET Atlassian Admin Header Connection
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://ax713gk4xl.execute-api.us-west-2.amazonaws.com/prod/user_team_info
    TRANSFER_TIMEOUT_LENGTH = 90
    UPLOAD_BODY:
      {
      "email": "@Value(email)"
      }
    UPLOAD_CONTENT_TYPE = JSON (application/json)
    UPLOAD_TYPE = Specify Upload Body
    USE_COOKIES = No
    VERIFY_SSL_CERTIFICATES = Yes
    -> JSONExtractor_7
Note: extract fields
JSONExtractor_7
    EXTRACT_QUERY_TABLE = team_name json["data"]["team"]["hierarchy"]["team"]["name"] team_lead_email json["data"]["team"]["hierarchy"]["team"]["lead"]["email"] team_alt_name json["data"]["team"]["hierarchy"]["team"]["alt_name"] department_name json["data"]["team"]["hierarchy"]["department"]["name"] department_lead_email json["data"]["team"]["hierarchy"]["department"]["lead"]["email"] division_name json["data"]["team"]["hierarchy"]["division"]["name"] division_lead_email json["data"]["team"]["hierarchy"]["division"]["lead"]["email"]
    JSON_DOCUMENT = @Value(_response_body)
    READ_FROM_FILE = NO
    EVALUATED -> AttributeKeeper_2
AttributeKeeper_2
    CREATE_BULK_MODE_FEATURES = NO
    KEEP_ATTRS = department_lead_email,department_name,division_lead_email,division_name,email,first,last,team_alt_name,team_lead_email,team_name,title
    -> Output (output)
Output (output)

FME custom transformer AtlassianIDGetter

Parameters:
- EMAIL = @Value(email)   # email

email (input)
    -> HTTPCaller_8
Note: get accountId
HTTPCaller_8
    AUTH_METHOD = Web Connection
    AUTH_NAMED_CONNECTION = SET Atlassian Admin Header Connection
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _user_response_body
    TARGET_ATTR_ENCODING = auto-detect
    TARGET_URL = https://safesoftware.atlassian.net/rest/api/3/user/search?query=@Value(email)
    TRANSFER_TIMEOUT_LENGTH = 90
    USE_COOKIES = No
    VERIFY_SSL_CERTIFICATES = Yes
    -> JSONExtractor
Note: extract accountId
JSONExtractor
    EXTRACT_QUERY_TABLE = "Atlassian Account ID" json[*]["accountId"]
    JSON_DOCUMENT = @Value(_user_response_body)
    READ_FROM_FILE = NO
    EVALUATED -> output (output)
output (output)
