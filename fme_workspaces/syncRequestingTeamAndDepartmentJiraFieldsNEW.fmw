FME workspace syncRequestingTeamAndDepartmentJiraFieldsNEW.fmw

Parameters:
- OLD_TEAM_NAME = PV & R   # old team name
- CHANGE = UPDATE   # update or add
- ORG_LEVEL = 3   # org level
- TEAM_NAME = PVR   # team name
- ALT_NAME = Databaes   # alt name

Creator_2
    GEOMTYPE = Geometry Object
    NUM = 1
    CREATED -> ParameterFetcher
ParameterFetcher
    ATTR_LIST = _OLD_TEAM_NAME $(OLD_TEAM_NAME) _TEAM_NAME $(TEAM_NAME) _ORG_LEVEL $(ORG_LEVEL) _CHANGE $(CHANGE) _ALT_NAME $(ALT_NAME)
    -> TestFilter_2
TestFilter_2
    DEFAULT_VALUE = <UNFILTERED>
    PASSED_TEST_GROUP_OUTPUT = FIRST
    TEST_LIST = "BOOL_OP,OR,COMPOSITE_TEST,""""""1"""""",TEST_CLAUSE,TEST @Value(_ORG_LEVEL) = 2",department,"BOOL_OP,OR,COMPOSITE_TEST,""""""1"""""",TEST_CLAUSE,TEST @Value(_ORG_LEVEL) = 3",team
    department -> AttributeCreator
    team -> NullAttributeMapper
AttributeCreator
    ATTR_TABLE:
      SET_TO customfield_id = 10601
      SET_TO context_id = 10819
    -> TestFilter
    -> HTTPCaller
Note: Add a logic to use alt_name only if Team Name is missing
NullAttributeMapper
    ATTRCHOICE = Selected Attributes
    ATTRLIST = $(TEAM_NAME)
    NEW_VALUE = @Value(_ALT_NAME)
    NULL_TREATMENT = New Value
    SOURCE_ATTR_VAL = Null
    -> AttributeCreator_2
AttributeCreator_2
    ATTR_TABLE:
      SET_TO customfield_id = 10602
      SET_TO context_id = 10820
    -> TestFilter
    -> HTTPCaller
Note: get current Requesting Department options from jira
HTTPCaller
    CONNECTION_TIMEOUT_LENGTH = 60
    CUSTOM_HEADERS = Authorization;Basic ZWxsYWluZS5jaGFuQHNhZmUuY29tOkFYZHF4VDRaSmZjdHV1dVRXUnF1QTRENw==
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://safesoftware.atlassian.net/rest/api/3/field/customfield_@Value(customfield_id)/context/@Value(context_id)/option
    TRANSFER_TIMEOUT_LENGTH = 90
    USE_COOKIES = No
    VERIFY_SSL_CERTIFICATES = Yes
    -> JSONFragmenter
JSONFragmenter
    EXPLODE_FORMAT = JSON
    EXTRACT_ATTR = No
    JSON_ATTR = _response_body
    JSON_QUERY = json["values"][*]
    READ_FROM_FILE = NO
    REJECT_EMPTY_LISTS = YES
    FRAGMENTS -> JSONExtractor
Note: extract name and id from json (we need id to update name)
JSONExtractor
    EXTRACT_QUERY_TABLE = name json["value"] id json["id"]
    JSON_DOCUMENT = @Value(_response_body)
    READ_FROM_FILE = NO
    EVALUATED -> FeatureMerger [REQUESTOR]
TestFilter
    DEFAULT_VALUE = <UNFILTERED>
    PASSED_TEST_GROUP_OUTPUT = FIRST
    TEST_LIST = "BOOL_OP,OR,COMPOSITE_TEST,""""""1"""""",TEST_CLAUSE,TEST @Value(_CHANGE) = UPDATE",update,"BOOL_OP,OR,COMPOSITE_TEST,""""""1"""""",TEST_CLAUSE,TEST @Value(_CHANGE) = ADD",add
    update -> FeatureMerger [SUPPLIER]
    add -> HTTPCaller_3
FeatureMerger
    ATTR_ACCUM_MODE = Merge Supplier
    ATTR_CONFLICT_RES = Use Requestor
    IGNORE_NULLS = No
    JOIN_KEYS = @Value(name) @Value(_OLD_TEAM_NAME) AUTO
    MERGE_TYPE = Attributes Only
    PROCESS_DUPS = NO
    REJECT_NULL_MISSING_KEYS = No
    SUPPLIERS_FIRST = No
    MERGED -> HTTPCaller_2
Note: update option name
HTTPCaller_2
    CONNECTION_TIMEOUT_LENGTH = 60
    CUSTOM_HEADERS = Authorization;Basic ZWxsYWluZS5jaGFuQHNhZmUuY29tOkFYZHF4VDRaSmZjdHV1dVRXUnF1QTRENw==
    ERROR_ATTR = _error
    FOLLOW_REDIRECTS = FOLLOW_WITH_GET
    HTTP_METHOD = PUT
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://safesoftware.atlassian.net/rest/api/3/field/customfield_@Value(customfield_id)/context/@Value(context_id)/option
    TRANSFER_TIMEOUT_LENGTH = 90
    UPLOAD_BODY:
      {
          "options": [
              {
                  "id": "@Value(id)",
                  "value": "@Value(_TEAM_NAME)"
              }
          ]
      }
    UPLOAD_CONTENT_TYPE = JSON (application/json)
    UPLOAD_TYPE = Specify Upload Body
    USE_COOKIES = No
    VERIFY_SSL_CERTIFICATES = Yes
Note: Add option
HTTPCaller_3
    CONNECTION_TIMEOUT_LENGTH = 60
    CUSTOM_HEADERS = Authorization;Basic ZWxsYWluZS5jaGFuQHNhZmUuY29tOkFYZHF4VDRaSmZjdHV1dVRXUnF1QTRENw==
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://safesoftware.atlassian.net/rest/api/3/field/customfield_@Value(customfield_id)/context/@Value(context_id)/option
    TRANSFER_TIMEOUT_LENGTH = 90
    UPLOAD_BODY:
      {
          "options": [
              {
                  "disabled": false,
                  "value": "@Value(_TEAM_NAME)"
              }
          ]
      }
    UPLOAD_CONTENT_TYPE = JSON (application/json)
    UPLOAD_TYPE = Specify Upload Body
    USE_COOKIES = No
    VERIFY_SSL_CERTIFICATES = Yes
