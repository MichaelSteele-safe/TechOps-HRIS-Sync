FME workspace HR - Jira to Quicksight - Recruitment Reader.fmw

Parameters:
- GSHEETS_CONNECTION_SAFE.GOOGLE-SHEETS.GOOGLESHEETS4 = Google Sheets - Iain   # "safe.google-sheets.Google Sheets" Google Sheets Connection

Writers:
- SAFE.GOOGLE-SHEETS.GOOGLESHEETS4_1: SAFE.GOOGLE-SHEETS.GOOGLESHEETS4

Creator
    GEOMTYPE = Geometry Object
    NUM = 1
    CREATED -> HTTPCaller_2
HTTPCaller_2
    AUTH_METHOD = Web Connection
    AUTH_NAMED_CONNECTION = Jira API Auth (HR Quicksight)
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://safesoftware.atlassian.net/rest/api/3/search
    TRANSFER_TIMEOUT_LENGTH = 90
    UPLOAD_BODY:
      {
        "expand": [
        ],
        "fields": [
          "summary",
          "status",
          "reporter",
          "issuelinks",
          "customfield_10297",
          "customfield_10601",
          "customfield_11645",
          "customfield_10602",
          "customfield_10134",
          "customfield_10279",
          "customfield_10128",
          "customfield_11652",
          "customfield_10557",
          "customfield_10558",
          "customfield_10551",
          "customfield_11647",
          "customfield_11646",
          "customfield_11692",
          "customfield_11944"
        ],
        "fieldsByKeys": false,
        "jql": "@Value(jql-query)",
        "maxResults": 100,
        "startAt": 0
      }
    UPLOAD_CONTENT_TYPE = JSON (application/json)
    UPLOAD_TYPE = Specify Upload Body
    USE_COOKIES = No
    VERIFY_SSL_CERTIFICATES = Yes
    -> JSONFlattener_3
JSONFlattener_3
    ERROR_LIST_ATTR = _json_error
    JSON_DOCUMENT = @Value(_response_body)
    NEW_ATTRIBUTES = total maxResults startAt
    READ_FROM_FILE = NO
    RECURSIVE = Yes
    -> AttributeCreator_3
AttributeCreator_3
    ATTR_TABLE = SET_TO numCalls (varchar(200)) = @ceil(@div(@Value(total),@Value(maxResults)),0)
    -> Cloner
Cloner
    COPIES = @Value(numCalls)
    COPYATT = _copynum
    COPY -> Tester_2
Note: "summary", / "status", / "reporter", / "issuelinks", / "customfield_10297", / "customfield_10601", / "customfield_11645", (req dept) / "customfield_10602", / "customfield_10134", / "customfield_10279", / "customfield_10128", (start date) / "customfield_11652", (start quarter) / "customfield_10557", (perm/tmp) / "customfield_10558", (ft/pt) / "customfield_10551", (dept) / "customfield_11647", (sal max) / "customfield_11646", (sal min) / "customfield_11692", (new or replacement) / "customfield_11944", (provisional start)
Tester_2
    BOOL_OP = OR
    TEST_CLAUSE = TEST @Value(_copynum) = 0
    TEST_MODE = TEST
    PASSED -> JSONFragmenter_2
    FAILED -> HTTPCaller_3
HTTPCaller_3
    AUTH_METHOD = Web Connection
    AUTH_NAMED_CONNECTION = Jira API Auth (HR Quicksight)
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://safesoftware.atlassian.net/rest/api/3/search
    TRANSFER_TIMEOUT_LENGTH = 90
    UPLOAD_BODY:
      {
        "expand": [
        ],
        "fields": [
          "summary",
          "status",
          "reporter",
          "issuelinks",
          "customfield_10297",
          "customfield_10601",
          "customfield_11645",
          "customfield_10602",
          "customfield_10134",
          "customfield_10279",
          "customfield_10128",
          "customfield_11652",
          "customfield_10557",
          "customfield_10558",
          "customfield_10551",
          "customfield_11647",
          "customfield_11646",
          "customfield_11692",
          "customfield_11944"
        ],
        "fieldsByKeys": false,
        "jql": "@Value(jql-query)",
        "maxResults": 100,
        "startAt": @mult(@Value(maxResults),@Value(_copynum))
      }
    UPLOAD_CONTENT_TYPE = JSON (application/json)
    UPLOAD_TYPE = Specify Upload Body
    USE_COOKIES = No
    VERIFY_SSL_CERTIFICATES = Yes
    -> JSONFragmenter_2
JSONFragmenter_2
    EXPLODE_FORMAT = JSON
    EXTRACT_ATTR = No
    JSON_ATTR = _response_body
    JSON_QUERY = json["issues"][*]
    READ_FROM_FILE = NO
    REJECT_EMPTY_LISTS = YES
    FRAGMENTS -> JSONFlattener_2
JSONFlattener_2
    ERROR_LIST_ATTR = _json_error
    JSON_DOCUMENT = @Value(_response_body)
    NEW_ATTRIBUTES = key fields.customfield_11645.value fields.customfield_10601.value fields.customfield_10602.value fields.summary fields.reporter.emailAddress fields.reporter.displayName fields.customfield_10297 fields.status.name fields.customfield_10134.requestType.name fields.customfield_11692.value fields.customfield_11647 fields.customfield_11646 fields.customfield_10128 fields.customfield_11652.value fields.customfield_10558.value fields.customfield_10551.value fields.customfield_10557.value fields.customfield_10279 fields.customfield_11944 fields.issuelinks fields.issuelinks{0}.outwardIssue.key fields.issuelinks{0}.outwardIssue.fields.summary fields.issuelinks{1}.outwardIssue.key fields.issuelinks{1}.outwardIssue.fields.summary fields.issuelinks{2}.outwardIssue.key fields.issuelinks{2}.outwardIssue.fields.summary
    READ_FROM_FILE = NO
    RECURSIVE = Yes
    -> AttributeSplitter
AttributeSplitter
    ATTR_NAME = fields.reporter.displayName
    DELIMITER = " "
    DROP_EMPTY_PARTS = No
    LIST_NAME = _list
    TRIM_OPTION = Both
    -> AttributeCreator_5
AttributeCreator_5
    ATTR_TABLE:
      SET_TO jira-reporter-first (varchar(200)) = @Value(_list{0})
      SET_TO merge (uint64) = 1
    -> AttributeManager_3
AttributeManager_3
    ATTR_TABLE:
      RENAME_SET_VALUE key > jira-key (buffer)
      RENAME_SET_VALUE fields.status.name > jira-status (buffer)
      RENAME_SET_VALUE fields.customfield_10134.requestType.name > jira-request-type (buffer)
      RENAME_SET_VALUE fields.customfield_10551.value > hiring-department (buffer)
      RENAME_SET_VALUE fields.customfield_10279 > job-title (buffer)
      RENAME_SET_VALUE fields.customfield_11692.value > budget-category (buffer)
      RENAME_SET_VALUE fields.customfield_10557.value > hire-category (buffer)
      RENAME_SET_VALUE fields.customfield_10558.value > ftpt (buffer)
      RENAME_SET_VALUE fields.customfield_11652.value > start-quarter (buffer)
      RENAME_SET_VALUE fields.customfield_10128 > start-date (buffer)
      RENAME_SET_VALUE fields.customfield_11647 > salary-max (buffer)
      RENAME_SET_VALUE fields.customfield_11944 > provisional-start (buffer)
      REMOVE fields.customfield_11646 (buffer)
      REMOVE fields.customfield_11645.value (buffer)
      REMOVE fields.summary (buffer)
      REMOVE fields.customfield_10601.value (buffer)
      REMOVE fields.customfield_10602.value (buffer)
      REMOVE fields.reporter.displayName (buffer)
      REMOVE fields.customfield_10297 (buffer)
      REMOVE numCalls (varchar(200))
      REMOVE _creation_instance (uint64)
      REMOVE total (buffer)
      REMOVE maxResults (buffer)
      REMOVE startAt (buffer)
      REMOVE _copynum (uint32)
      REMOVE _response_body (buffer)
      REMOVE _http_status_code (buffer)
      REMOVE json_type (buffer)
      REMOVE json_index (uint32)
      REMOVE jira-reporter-first (varchar(200))
      REMOVE merge (uint64)
      REMOVE jql-query (varchar(200))
      REMOVE fields.reporter.emailAddress (buffer)
      REMOVE _list{} (varchar(200))
      RENAME_SET_VALUE fields.issuelinks{0}.outwardIssue.key > outward-0-id (buffer)
      RENAME_SET_VALUE fields.issuelinks{0}.outwardIssue.fields.summary > outward-0-summary (buffer)
      RENAME_SET_VALUE fields.issuelinks{1}.outwardIssue.key > outward-1-id (buffer)
      RENAME_SET_VALUE fields.issuelinks{1}.outwardIssue.fields.summary > outward-1-summary (buffer)
      RENAME_SET_VALUE fields.issuelinks{2}.outwardIssue.key > outward-2-id (buffer)
      RENAME_SET_VALUE fields.issuelinks{2}.outwardIssue.fields.summary > outward-2-summary (buffer)
    USER_EXPOSED_ATTRIBUTES = reporter.emailAddress,reporter.displayName,jira-reporter-first,issueKey,fields.customfield_11652
    -> TestFilter
TestFilter
    DEFAULT_VALUE = Co-Op
    PASSED_TEST_GROUP_OUTPUT = FIRST
    TEST_LIST = "BOOL_OP,OR,COMPOSITE_TEST,""""""1"""""",TEST_CLAUSE,TEST @Value(jira-request-type) = Hiring Request (Permanent/Temporary)",Staff
    Staff -> TestFilter_2
TestFilter_2
    DEFAULT_VALUE = In Process
    PASSED_TEST_GROUP_OUTPUT = FIRST
    TEST_LIST = "BOOL_OP,OR,COMPOSITE_TEST,""""""1"""""",TEST_CLAUSE,TEST @Value(jira-status) = Rejected",Rejected,"BOOL_OP,OR,COMPOSITE_TEST,""""""1"""""",TEST_CLAUSE,TEST @Value(jira-status) = Deferred",Deferred,"BOOL_OP,OR,COMPOSITE_TEST,""""""1"""""",TEST_CLAUSE,TEST @Value(jira-status) = Hired",Hired,"BOOL_OP,OR,COMPOSITE_TEST,""""""1"""""",TEST_CLAUSE,TEST @Value(jira-status) = Approved",Approved
    Hired -> TestFilter_3
    Hired -> TestFilter_5
    Approved -> TestFilter_3
    Approved -> TestFilter_5
    In Process -> TestFilter_3
    In Process -> TestFilter_5
Tester_4
    BOOL_OP = COMPOSITE
    COMPOSITE_TEST = 1 AND 2
    TEST_CLAUSE:
      CASE_INSENSITIVE_TEST @Value(outward-0-id) CONTAINS IS-
      CASE_INSENSITIVE_TEST @Value(outward-0-summary) CONTAINS Hire
    TEST_MODE = CASE_INSENSITIVE_TEST
    PASSED -> AttributeCreator
    FAILED -> Tester_5
AttributeCreator
    ATTR_TABLE = SET_TO is-key (varchar(200)) = @Value(outward-0-id)
    -> Sorter_5
Tester_5
    BOOL_OP = COMPOSITE
    COMPOSITE_TEST = 1 AND 2
    TEST_CLAUSE:
      CASE_INSENSITIVE_TEST @Value(outward-1-id) CONTAINS IS-
      CASE_INSENSITIVE_TEST @Value(outward-1-summary) CONTAINS Hire
    TEST_MODE = CASE_INSENSITIVE_TEST
    PASSED -> AttributeCreator_2
    FAILED -> Tester_6
AttributeCreator_2
    ATTR_TABLE = SET_TO is-key (varchar(200)) = @Value(outward-1-id)
    -> Sorter_5
Tester_6
    BOOL_OP = COMPOSITE
    COMPOSITE_TEST = 1 AND 2
    TEST_CLAUSE:
      CASE_INSENSITIVE_TEST @Value(outward-2-id) CONTAINS IS-
      CASE_INSENSITIVE_TEST @Value(outward-2-summary) CONTAINS Hire
    TEST_MODE = CASE_INSENSITIVE_TEST
    PASSED -> AttributeCreator_4
    FAILED -> Sorter_5
AttributeCreator_4
    ATTR_TABLE = SET_TO is-key (varchar(200)) = @Value(outward-2-id)
    -> Sorter_5
Sorter_5
    SORT_PARM = Quarter NATURAL DESCENDING Department NATURAL ASCENDING budget-category NATURAL ASCENDING
    SORTED -> Sorter_3
Sorter_3
    SORT_PARM = Quarter NATURAL DESCENDING Provisional Start NATURAL DESCENDING
    SORTED -> TestFilter_7
TestFilter_7
    DEFAULT_VALUE = <UNFILTERED>
    PASSED_TEST_GROUP_OUTPUT = FIRST
    TEST_LIST = "BOOL_OP,OR,COMPOSITE_TEST,""""""1"""""",TEST_CLAUSE,TEST @Value(budget-category) = New Headcount",New Headcount,"BOOL_OP,OR,COMPOSITE_TEST,""""""1"""""",TEST_CLAUSE,TEST @Value(budget-category) = Replacement Headcount",Replacement
    New Headcount -> AttributeManager_5
    New Headcount -> JSONFragmenter [off]
    Replacement -> AttributeManager_2
JSONFragmenter
    EXPLODE_FORMAT = JSON
    EXTRACT_ATTR = Yes
    JSON_ATTR = fields.issuelinks
    JSON_QUERY = json[*]
    READ_FROM_FILE = NO
    RECURSIVE = YES
    REJECT_EMPTY_LISTS = NO
AttributeManager_5
    ATTR_TABLE:
      RENAME_SET_VALUE Issue ID > HR Ticket (buffer) = =HYPERLINK("https://safesoftware.atlassian.net/browse/@Value(HR Ticket)", "@Value(HR Ticket)")
      RENAME_SET_VALUE is-key > IS Ticket (varchar(200)) = =HYPERLINK("https://safesoftware.atlassian.net/browse/@Value(IS Ticket)", "@Value(IS Ticket)")
      REMOVE budget-category (buffer)
      REMOVE fields.issuelinks (buffer)
      REMOVE outward-0-id (buffer)
      REMOVE outward-0-summary (buffer)
      REMOVE outward-1-id (buffer)
      REMOVE outward-1-summary (buffer)
      REMOVE outward-2-id (buffer)
      REMOVE outward-2-summary (buffer)
    -> Counter
Counter
    CNT_ATTR = _count
    DOMAIN = counter
    SCOPE = Global
    START = 0
    -> ListBuilder
AttributeManager_7
    ATTR_TABLE:
      REMOVE _count (int64)
      REMOVE _copynum (uint32)
      REMOVE Boundary (varchar(200))
      REMOVE _element_index (uint32)
    -> New Headcount (writer SAFE.GOOGLE-SHEETS.GOOGLESHEETS4_1)
New Headcount (writer SAFE.GOOGLE-SHEETS.GOOGLESHEETS4_1)
    attributes: Quarter text, Provisional Start text, Department text, Status text, FTPT text, Title text, HR Ticket text, IS Ticket text
AttributeManager_2
    ATTR_TABLE:
      REMOVE sheet (varchar(21))
      REMOVE budget-category (buffer)
    -> Replacement Headcount (writer SAFE.GOOGLE-SHEETS.GOOGLESHEETS4_1)
Replacement Headcount (writer SAFE.GOOGLE-SHEETS.GOOGLESHEETS4_1)
    attributes: Quarter text, Provisional Start text, Department text, Status text, FTPT text, Issue ID text, Title text, is-key text, fields.issuelinks text, outward-0-id text, outward-0-summary text, outward-1-id text, outward-1-summary text, outward-2-id text, outward-2-summary text

Bookmark: Specific Criteria for Quicksight Finance Report
TestFilter_3
    DEFAULT_VALUE = Other
    PASSED_TEST_GROUP_OUTPUT = FIRST
    TEST_LIST = "BOOL_OP,OR,COMPOSITE_TEST,""""""1"""""",TEST_CLAUSE,TEST @Value(hire-category) = Permanent",Permanent,"BOOL_OP,OR,COMPOSITE_TEST,""""""1"""""",TEST_CLAUSE,TEST @Value(hire-category) = Temporary",Temporary
    Permanent -> TestFilter_4
TestFilter_4
    DEFAULT_VALUE = No Quarter
    PASSED_TEST_GROUP_OUTPUT = FIRST
    TEST_LIST = "BOOL_OP,OR,COMPOSITE_TEST,""""""1"""""",TEST_CLAUSE,TEST start-quarter ATTRIBUTE_HAS_A_VALUE """,Quarter
    Quarter -> SubstringExtractor
SubstringExtractor
    END = 6
    RESULT_ATTR = start-quarter
    SRC_STRING = @Value(start-quarter)
    START = 0
    -> Sorter
Sorter
    SORT_PARM = jira-request-type NATURAL ASCENDING hiring-department NATURAL ASCENDING budget-category NATURAL ASCENDING start-quarter NATURAL ASCENDING
    SORTED -> Inspector
Inspector

Bookmark: Broader Criteria for Security/IT Report
TestFilter_5
    DEFAULT_VALUE = Other
    PASSED_TEST_GROUP_OUTPUT = FIRST
    TEST_LIST = "BOOL_OP,OR,COMPOSITE_TEST,""""""1"""""",TEST_CLAUSE,TEST @Value(hire-category) = Permanent",Permanent,"BOOL_OP,OR,COMPOSITE_TEST,""""""1"""""",TEST_CLAUSE,TEST @Value(hire-category) = Temporary",Temporary
    Permanent -> TestFilter_6
    Temporary -> TestFilter_6
TestFilter_6
    DEFAULT_VALUE = No Quarter
    PASSED_TEST_GROUP_OUTPUT = FIRST
    TEST_LIST = "BOOL_OP,OR,COMPOSITE_TEST,""""""1"""""",TEST_CLAUSE,TEST start-quarter ATTRIBUTE_HAS_A_VALUE """,Quarter
    Quarter -> SubstringExtractor_2
SubstringExtractor_2
    END = 6
    RESULT_ATTR = start-quarter
    SRC_STRING = @Value(start-quarter)
    START = 0
    -> Sorter_2
Sorter_2
    SORT_PARM = jira-request-type NATURAL ASCENDING start-quarter NATURAL DESCENDING hiring-department NATURAL ASCENDING budget-category NATURAL ASCENDING
    SORTED -> AttributeManager
AttributeManager
    ATTR_TABLE:
      REMOVE start-date (buffer)
      REMOVE salary-max (buffer)
    -> AttributeManager_4
AttributeManager_4
    ATTR_TABLE:
      RENAME_SET_VALUE start-quarter > Quarter (buffer)
      RENAME_SET_VALUE provisional-start > Provisional Start (buffer)
      RENAME_SET_VALUE hiring-department > Department (buffer)
      RENAME_SET_VALUE jira-status > Status (buffer)
      RENAME_SET_VALUE jira-key > Issue ID (buffer)
      RENAME_SET_VALUE job-title > Title (buffer)
      RENAME_SET_VALUE ftpt > FTPT (buffer)
      REMOVE jira-request-type (buffer)
      REMOVE hire-category (buffer)
      SET_TO is-key (varchar(200))
    -> Tester_4

Bookmark: Line Breaks
ListBuilder
    LIST_ATTRS_TO_INCLUDE = _count Quarter Department FTPT Provisional Start Status Title HR Ticket IS Ticket
    LIST_NAME = _quarter_list
    -> PythonCaller_2
PythonCaller_2
    PYTHONSOURCE:
      import fme
      import fmeobjects


      class FeatureProcessor(object):
          """Template Class Interface:
          When using this class, make sure its name is set as the value of the 'Class to Process Features'
          transformer parameter.
          """

          def __init__(self):
              """Base constructor for class members."""
              pass

          def has_support_for(self, support_type: int):
              """This method is called by FME to determine if the PythonCaller supports Bulk mode,
              which allows for significant performance gains when processing large numbers of features.
              Bulk mode cannot always be supported.
              More information available in transformer help.
              """
              return support_type == fmeobjects.FME_SUPPORT_FEATURE_TABLE_SHIM

          def input(self, feature: fmeobjects.FMEFeature):
              """This method is called for each feature which enters the PythonCaller.
              Processed input features can be emitted from this method using self.pyoutput().
              If knowledge of all input features is required for processing, then input features should be
              cached to a list instance variable and processed using group processing or in the close() method.
              """
              quarters = []
              index = 0

              # Dynamically populate the quarters list with values from the list attribute
              while True:
                  try:
                      # Retrieve Quarter value for the current index in the list
                      quarter = feature.getAttribute(f"_quarter_list{{{index}}}.Quarter")
                      if quarter is None:
                          break  # Exit if no more entries in the list

                      # Append a tuple (quarter, index) to keep track of each item's position
                      quarters.append((quarter, index))
                      index += 1
                  except:
                      break  # Exit the loop if any issue accessing list items

              # Loop through quarters to detect changes and set Boundary attributes
              for i in range(len(quarters) - 1):
                  current_quarter, current_index = quarters[i]
                  next_quarter, next_index = quarters[i + 1]

                  # Check if there's a boundary (change in Quarter value)
                  if current_quarter != next_quarter:
                      # Set Boundary="Yes" for the current item in _quarter_list
                      feature.setAttribute(f"_quarter_list{{{current_index}}}.Boundary", "Yes")
                      # Optionally, also set Boundary="Yes" for the next item
                      #feature.setAttribute(f"_quarter_list{{{next_index}}}.Boundary", "Yes")
                  #else:
                      # Set Boundary="No" if there is no change
                      #feature.setAttribute(f"_quarter_list{{{current_index}}}.Boundary", "No")

              self.pyoutput(feature)

          def close(self):
              """This method is called once all the FME Features have been processed from input()."""
              pass

          def process_group(self):
              """This method is called by FME for each group when group processing mode is enabled.
              This implementation should reset any instance variables used for the next group.
              Bulk mode should not be enabled when using group processing.
              More information available in transformer help.
              """
              pass
    PYTHONSYMBOL = FeatureProcessor
    -> ListExploder
ListExploder
    ATTR_ACCUM_MODE = Merge List Attributes
    ATTR_CONFLICT_RES = Use List Attribute Values
    INDEX_ATTR = _element_index
    LIST_ATTR = _quarter_list{}
    ELEMENTS -> AttributeExposer
AttributeExposer
    ATTR_TABLE = Boundary,
    -> Tester
Tester
    BOOL_OP = OR
    TEST_CLAUSE = TEST @Value(Boundary) = Yes
    TEST_MODE = TEST
    PASSED -> Cloner_2
    FAILED -> Sorter_4
Cloner_2
    COPIES = 3
    COPYATT = _copynum
    COPY -> Tester_3
Tester_3
    BOOL_OP = OR
    TEST_CLAUSE = TEST @Value(_copynum) > 0
    TEST_MODE = TEST
    PASSED -> AttributeManager_6
    FAILED -> Sorter_4
AttributeManager_6
    ATTR_TABLE:
      SET_TO Quarter (buffer)
      REMOVE _element_index (uint32)
      SET_TO Boundary (varchar(200))
      SET_TO Provisional Start (buffer)
      SET_TO Department (buffer)
      SET_TO Status (buffer)
      SET_TO FTPT (buffer)
      SET_TO Title (buffer)
      SET_TO HR Ticket (buffer)
      SET_TO IS Ticket (varchar(200))
    USER_EXPOSED_ATTRIBUTES = Issue ID
    -> Sorter_4
Sorter_4
    SORT_PARM = _count NATURAL ASCENDING _copynum NATURAL ASCENDING
    SORTED -> AttributeManager_7
