FME workspace UkgImport.fmw

Parameters:
- SLACK_NOTIFICATION_WEBHOOK = https://hooks.slack.com/services/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   # webhook to send notification to slack
- DestDataset_MYSQL_DB_9 = set-rds-user   # (MySQL compatible) Connection
- DestDataset_MYSQL_DB_7 = set-rds-user   # (MySQL compatible) Connection
- DestDataset_MYSQL_DB_6 = set-rds-user   # (MySQL compatible) Connection
- DestDataset_MYSQL_DB_8 = set-rds-user   # (MySQL compatible) Connection
- DestDataset_MYSQL_DB = set-rds-user   # (MySQL compatible) Connection

Writers:
- CSV2_1: CSV2 to /Users/ellaine.chan/Desktop
- MYSQL_DB_2: MYSQL_DB to $(DestDataset_MYSQL_DB_9)
- MYSQL_DB_3: MYSQL_DB to $(DestDataset_MYSQL_DB_7)
- MYSQL_DB_4: MYSQL_DB to $(DestDataset_MYSQL_DB_6)
- MYSQL_DB_1: MYSQL_DB to $(DestDataset_MYSQL_DB)
- MYSQL_DB_5: MYSQL_DB to $(DestDataset_MYSQL_DB_8)

Note: UKG Generated reports are sent to hrisautomation@safe.com, picked up by Google App Scripts and dropped to Google Drive. This workspace reads the latest CSV files to migrate data into our database. / Author: Ellaine Chan
Creator
    GEOMTYPE = Geometry Object
    NUM = 1
    CREATED -> GoogleDriveConnector
Note: List all files in the drive
GoogleDriveConnector
    GOOGLEDRIVE_NAMED_CONNECTION = ellaine.chan Google Drive
    OPERATION_TYPE = List
    PARAMETER_SETUP = _FME_FILES;1rjRm_CFXUfnNy3VOpvD_QQaHeIFgCVpN;_FME_INCLUDE_SUBFOLDERS;Yes;_FME_OBJECT_NAME_ATTRIBUTE;_name;_FME_OBJECT_ID_ATTRIBUTE;_id;_FME_OBJECT_PATH_ATTRIBUTE;_sharable_link;_FME_OBJECT_SIZE_ATTRIBUTE;_file_size;_FME_OBJECT_MODIFIED_ATTRIBUTE;_file_last_modified;_FME_OBJECT_TYPE_ATTRIBUTE;_file_or_folder;_FME_OBJECT_RELATIVE_PATH_ATTRIBUTE;_relative_path;FME_CONTROLLER_QUERY_FILE;transformers/dependencies/googledrive/List.fme;FME_CONTROLLER_CHOICE;List
    -> Sorter
Note: sort by date
Sorter
    SORT_PARM = _file_last_modified NATURAL DESCENDING
    SORTED -> Tester
Tester
    BOOL_OP = OR
    TEST_CLAUSE = CASE_INSENSITIVE_TEST @Value(_name) CONTAINS Employee
    TEST_MODE = CASE_INSENSITIVE_TEST
    PASSED -> Sampler
    FAILED -> Sampler_2
HTTPCaller_4
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - Employee Added",
              "text": "Employee @Value(id) (@Value(display_name) @Value(last))",
              "color": "good"
          }
          ]
      }
    UPLOAD_CONTENT_TYPE = Text (text/plain)
    UPLOAD_TYPE = Specify Upload Body
    USE_COOKIES = No
    VERIFY_SSL_CERTIFICATES = Yes

Bookmark: get slack ID and avatar if null
SQLCreator_2
    DATASET = set-rds-user
    EXPOSED_ATTRIBUTE_LIST = email,id
    FORMAT = MYSQL
    MYSQL_HANDLE_UTC_OFFSET = Yes
    MYSQL_NAMED_CONNECTION = set-rds-user
    MYSQL_QUERY_FEATURE_TYPES_FOR_MERGE_FILTERS = Yes
    OUTPUT_FEATURES_DISPLAY = Schema and Data Features
    SQL_STATEMENT:
      select id, email from users.ukg_users
      where ( slack_id IS NULL or slack_id = "" or avatar_url = "" or avatar_url IS NULL)
      and deactivated is NULL
    RESULT -> HTTPCaller_17
HTTPCaller_17
    CONNECTION_TIMEOUT_LENGTH = 60
    CUSTOM_HEADERS = Authorization;Bearer xoxb-4573705574-1307285409845-phM9iicEYuXWd34uZcR4oVOH
    ERROR_ATTR = _error
    FOLLOW_REDIRECTS = FOLLOW_WITH_GET
    HTTP_METHOD = GET
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = https://slack.com/api/users.lookupByEmail?email=@Value(email)@safe.com
    TRANSFER_TIMEOUT_LENGTH = 90
    USE_COOKIES = No
    VERIFY_SSL_CERTIFICATES = Yes
    -> JSONExtractor_4
JSONExtractor_4
    EXTRACT_QUERY_TABLE = slack_id json["user"]["id"] avatar_url json["user"]["profile"]["image_192"]
    JSON_DOCUMENT = @Value(_response_body)
    READ_FROM_FILE = NO
    EVALUATED -> SQLExecutor_4 [INITIATOR]
SQLExecutor_4
    COMBINE_ATTRS = Result Attributes Only
    COMBINE_GEOM = Initiator Geometry Only
    DATASET = set-rds-user
    FORMAT = MYSQL
    MYSQL_HANDLE_UTC_OFFSET = Yes
    MYSQL_NAMED_CONNECTION = set-rds-user
    MYSQL_QUERY_FEATURE_TYPES_FOR_MERGE_FILTERS = Yes
    OUTPUT_FEATURES_DISPLAY = Schema and Data Features
    SQL_STATEMENT:
      UPDATE users.ukg_users
      set slack_id = "@Value(slack_id)", avatar_url = "@Value(avatar_url)"
      where id = "@Value(id)"

Bookmark: employees
Note: Only process the latest 2 files
Sampler
    RATE = 2
    SAMPLE_MODE = No
    SAMPLE_TYPE_LONG = First N Features
    SAMPLED -> Counter
Counter
    CNT_ATTR = _count
    DOMAIN = counter
    SCOPE = Global
    START = 0
    -> GoogleDriveConnector_2
    -> Logger
Note: download latest two employee csv
GoogleDriveConnector_2
    GOOGLEDRIVE_NAMED_CONNECTION = ellaine.chan Google Drive
    OPERATION_TYPE = Download
    PARAMETER_SETUP = _FME_FILES;@Value(_id);_FME_DATA_TARGET;Attribute;_FME_TARGET_FOLDER;<Unused>;_FME_INCLUDE_SUBFOLDERS;<Unused>;_FME_TARGET_ATTRIBUTE;_contents;FME_CONTROLLER_QUERY_FILE;transformers/dependencies/googledrive/Download.fme;FME_CONTROLLER_CHOICE;Download
    -> Tester_8
Tester_8
    BOOL_OP = OR
    TEST_CLAUSE = TEST @Value(_count) = 0
    TEST_MODE = TEST
    PASSED -> TempPathnameCreator
    FAILED -> TempPathnameCreator_2
TempPathnameCreator
    EXTENSION = .csv
    PATHNAME_ATTR = _pathname
    -> AttributeFileWriter
Note: latest version
AttributeFileWriter
    CHAR_ENCODING = fme-system
    FILE_NAME = @Value(_pathname)
    OVERWRITE_FILE = Overwrite file
    SOURCE_ATTR = _contents
    -> FeatureReader_5 [INITIATOR]
FeatureReader_5
    ATTRS_TO_EXPOSE = Last Name First Name Preferred First Name Employee Number Employee Email Job Org Level 2 Code Org Level 2 Org Level 3 Code OL3 Alt Org Level 3 Work Extension Slack ID AD Login Office Number Office Floor Former Co-op OL2 Alt Org Level 1
    ATTR_ACCUM_MODE = Only Use Result
    COMBINE_GEOM = Use Result
    CSV2_CASE_SENSITIVE_FIELD_NAMES = Yes
    CSV2_CHUNK_SIZE = 100000
    CSV2_DATA_START_LINE = 2
    CSV2_DELIMITER = auto
    CSV2_ENCODING = UTF-8
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 10000
    CSV2_SCAN_TYPES = Yes
    CSV2_SKIP_DUPLICATE_DELIMITERS = No
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_USE_CUSTOM_SCHEMA = YES
    DATASET = @Value(_pathname)
    FORMAT = CSV2
    INTERACT = NONE
    OUTPUT_FEATURES_DISPLAY = Schema and Data Features
    <OTHER> -> AttributeCreator_2
Note: state is new
AttributeCreator_2
    ATTR_TABLE = SET_TO state = new
    -> Tester_2
TempPathnameCreator_2
    EXTENSION = .csv
    PATHNAME_ATTR = _pathname
    -> AttributeFileWriter_3
Note: Older version
AttributeFileWriter_3
    CHAR_ENCODING = fme-system
    FILE_NAME = @Value(_pathname)
    OVERWRITE_FILE = Overwrite file
    SOURCE_ATTR = _contents
    -> FeatureReader_3 [INITIATOR]
FeatureReader_3
    ATTRS_TO_EXPOSE = Last Name First Name Preferred First Name Employee Number Employee Email Job Org Level 2 Code Org Level 2 Org Level 3 Code Org Level 3 Work Extension AD Login Slack ID Office Number Office Floor Former Co-op OL3 Alt OL2 Alt Org Level 1
    ATTR_ACCUM_MODE = Only Use Result
    COMBINE_GEOM = Use Result
    CSV2_CASE_SENSITIVE_FIELD_NAMES = Yes
    CSV2_CHUNK_SIZE = 100000
    CSV2_DATA_START_LINE = 2
    CSV2_DELIMITER = auto
    CSV2_ENCODING = UTF-8
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 10000
    CSV2_SCAN_TYPES = Yes
    CSV2_SKIP_DUPLICATE_DELIMITERS = No
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_USE_CUSTOM_SCHEMA = YES
    DATASET = @Value(_pathname)
    FORMAT = CSV2
    INTERACT = NONE
    OUTPUT_FEATURES_DISPLAY = Schema and Data Features
    <OTHER> -> AttributeCreator
    <REJECTED> -> Terminator
Note: state is old
AttributeCreator
    ATTR_TABLE = SET_TO state = old
    -> Tester_2
Tester_2
    BOOL_OP = OR
    TEST_CLAUSE = TEST Employee Email ATTRIBUTE_HAS_A_VALUE ""
    TEST_MODE = TEST
    PASSED -> AttributeCreator_8
Note: create display name, default to preferred first name
AttributeCreator_8
    ATTR_TABLE = SET_TO display_name = @Value(Preferred First Name)
    -> NullAttributeMapper_9
Note: use first name as display name if null
NullAttributeMapper_9
    ATTRCHOICE = Selected Attributes
    ATTRLIST = display_name
    NEW_VALUE = @Value(First Name)
    NULL_TREATMENT = New Value
    SOURCE_ATTR_VAL = Null Empty "Missing (Selected Attributes Only)"
    -> NullAttributeMapper
    -> SQLExecutor [INITIATOR]
Note: use org 2 code as team_id if org 3 code is empty
NullAttributeMapper
    ATTRCHOICE = Selected Attributes
    ATTRLIST = Org Level 3 Code
    NEW_VALUE = @Value(Org Level 2 Code)
    NULL_TREATMENT = New Value
    SOURCE_ATTR_VAL = Null Empty "Missing (Selected Attributes Only)"
    -> NullAttributeMapper_6
Note: use org 2 as team if org 3 is empty
NullAttributeMapper_6
    ATTRCHOICE = Selected Attributes
    ATTRLIST = Org Level 3
    NEW_VALUE = @Value(Org Level 2)
    NULL_TREATMENT = New Value
    SOURCE_ATTR_VAL = Null Empty "Missing (Selected Attributes Only)"
    -> AttributeManager_7
Note: rename attributes to match db column names and remove "@safe.com" from email
AttributeManager_7
    ATTR_TABLE:
      RENAME_SET_VALUE Last Name > last
      RENAME_SET_VALUE First Name > first
      RENAME_SET_VALUE Preferred First Name > preferred_first_name
      RENAME_SET_VALUE Employee Number > id
      RENAME_SET_VALUE Job > title
      RENAME_SET_VALUE Org Level 3 Code > team_id
      RENAME_SET_VALUE Work Extension > work_extension
      RENAME_SET_VALUE AD Login > ldap
      REMOVE Slack ID
      RENAME_SET_VALUE Office Number > office_number
      RENAME_SET_VALUE Office Floor > office_floor
      RENAME_SET_VALUE Former Co-op > former_coop
    -> AttributeCreator_5
AttributeCreator_5
    ATTR_TABLE:
      SET_TO fme_where = id = @Value(id)
      SET_TO email = @ReplaceString(@Value(Employee Email),"@safe.com","")
    -> DateTimeStamper
DateTimeStamper
    DATETIME_ATTR = last_update
    INCLUDE_FRAC_SECONDS = YES
    INCLUDE_OFFSET = NO
    STAMP_TYPE = datetime
    TIMEZONE = utc
    -> Tester_9
Note: Is this the previous/older version?
Tester_9
    BOOL_OP = OR
    TEST_CLAUSE = TEST @Value(state) = old
    TEST_MODE = TEST
    PASSED -> ChangeDetector [ORIGINAL]
    FAILED -> ChangeDetector [REVISED]
    FAILED -> ukg_users (writer MYSQL_DB_5)
ChangeDetector
    BLANK_AND_MISSING_DIFFER = No
    BLANK_AND_MISSING_NAMES_TRAITS_DIFFER = No
    CHECK_COORDINATE_SYSTEMS = No
    CHECK_TYPES_AND_ENCODINGS = No
    LENIENT_MATCH = No
    MATCH = FULL
    MATCHATTRS = preferred_first_name title first last team_id office_floor office_number work_extension
    MATCH_STRATEGY = Match Selected Attributes
    PREEMPTIVE_ATTRS = id
    UNCHANGED_OUTPUT = Output Original
    UPDATED_LIST_NAME = _change_detection_list
    UPSERT_MODE = No
    UPDATED -> ListExploder
    INSERTED -> ukg_users (writer MYSQL_DB_1)
    INSERTED -> HTTPCaller_4
    DELETED -> SQLExecutor_2 [INITIATOR]
    DELETED -> HTTPCaller_3
Note: Get one feature per change
ListExploder
    ATTR_ACCUM_MODE = Merge List Attributes
    ATTR_CONFLICT_RES = Use List Attribute Values
    INDEX_ATTR = _element_index
    LIST_ATTR = _change_detection_list{}
    ELEMENTS -> Tester_7
Tester_7
    BOOL_OP = OR
    TEST_CLAUSE = TEST @Value(attributeName) = team_id
    TEST_MODE = TEST
    PASSED -> SQLExecutor_6 [INITIATOR]
    FAILED -> NullAttributeMapper_8
ukg_users (writer MYSQL_DB_1)
    attributes: email varchar(200), last varchar(200), first varchar(200), preferred_first_name varchar(200), id varchar(200), title varchar(200), team_id varchar(200), work_extension varchar(200), ldap varchar(200), office_number varchar(200), office_floor varchar(200), former_coop varchar(200), last_update text
ukg_users (writer MYSQL_DB_5)
    attributes: email varchar(200), state varchar(200), last varchar(200), first varchar(200), preferred_first_name varchar(200), id varchar(200), title varchar(200), team_id varchar(200), work_extension varchar(200), ldap varchar(200), office_number varchar(200), office_floor varchar(200), former_coop varchar(200), last_update text, deactivated text
Terminator
    MESSAGE = Translation Terminated
Logger
    LOG_FEATURE = LOG_ONLY
    MAXCOORDS = 20
    MAXFEATS = 20
    MESSAGE = Downloading... @Value(_name)
    SEVERITY = INFO

Bookmark: Update Employee DB Tasks
Note: Update jira avatar
SQLExecutor [off]
    COMBINE_ATTRS = Result Attributes Only
    COMBINE_GEOM = Initiator Geometry Only
    DATASET = set-rds-user
    FORMAT = MYSQL
    MYSQL_HANDLE_UTC_OFFSET = Yes
    MYSQL_NAMED_CONNECTION = set-rds-user
    MYSQL_QUERY_FEATURE_TYPES_FOR_MERGE_FILTERS = Yes
    OUTPUT_FEATURES_DISPLAY = Schema and Data Features
    SQL_STATEMENT:
      UPDATE users.ukg_users
      set jira_avatar = "@Value(jira_avatar)"
      WHERE id = @Value(Employee Number)
SQLExecutor_6
    ATTR_IGNORE_NULLS = Yes
    COMBINE_ATTRS = Keep Initiator Attributes if Conflict
    COMBINE_GEOM = Initiator Geometry Only
    DATASET = set-rds-user
    EXPOSED_ATTRIBUTE_LIST = original_team_name
    FORMAT = MYSQL
    MYSQL_HANDLE_UTC_OFFSET = Yes
    MYSQL_NAMED_CONNECTION = set-rds-user
    MYSQL_QUERY_FEATURE_TYPES_FOR_MERGE_FILTERS = Yes
    OUTPUT_FEATURES_DISPLAY = Schema and Data Features
    SQL_STATEMENT = select name as original_team_name from users.ukg_teams where id = "@Value(originalValue)"
    RESULT -> SQLExecutor_7 [INITIATOR]
SQLExecutor_7
    ATTR_IGNORE_NULLS = Yes
    COMBINE_ATTRS = Keep Initiator Attributes if Conflict
    COMBINE_GEOM = Initiator Geometry Only
    DATASET = set-rds-user
    EXPOSED_ATTRIBUTE_LIST = revised_team_name,revised_alt_name
    FORMAT = MYSQL
    MYSQL_HANDLE_UTC_OFFSET = Yes
    MYSQL_NAMED_CONNECTION = set-rds-user
    MYSQL_QUERY_FEATURE_TYPES_FOR_MERGE_FILTERS = Yes
    OUTPUT_FEATURES_DISPLAY = Schema and Data Features
    SQL_STATEMENT = select name as revised_team_name, alt_name as revised_alt_name from users.ukg_teams where id = "@Value(revisedValue)"
    RESULT -> HTTPCaller_7
Note: notify techops_automation of employee team updates
HTTPCaller_7
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - Employee updated",
              "text": "Employee @Value(id) (@Value(display_name) @Value(last)) \n Field: @Value(attributeName)\n  ~@Value(originalValue)/@Value(original_team_name)~ -> @Value(revisedValue)/@Value(revised_team_name)",
              "color": "warning"
          }
          ]
      }
    UPLOAD_CONTENT_TYPE = Text (text/plain)
    UPLOAD_TYPE = Specify Upload Body
    USE_COOKIES = No
    VERIFY_SSL_CERTIFICATES = Yes
Note: notify techops_automation of employee activation
NullAttributeMapper_8
    ATTRCHOICE = Selected Attributes
    ATTRLIST = originalValue revisedValue
    NEW_VALUE = Null
    NULL_TREATMENT = New Value
    SOURCE_ATTR_VAL = Null Empty "Missing (Selected Attributes Only)"
    -> HTTPCaller
Note: notify techops_automation of updates
HTTPCaller
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - Employee updated",
              "text": "Employee @Value(id) (@Value(display_name) @Value(last)) \n Field: @Value(attributeName)\n  ~@Value(originalValue)~ -> @Value(revisedValue)",
              "color": "warning"
          }
          ]
      }
    UPLOAD_CONTENT_TYPE = Text (text/plain)
    UPLOAD_TYPE = Specify Upload Body
    USE_COOKIES = No
    VERIFY_SSL_CERTIFICATES = Yes

Bookmark: Employee Deactivation DB tasks
Note: set deactivated date
SQLExecutor_2
    COMBINE_ATTRS = Result Attributes Only
    COMBINE_GEOM = Initiator Geometry Only
    DATASET = set-rds-user
    FORMAT = MYSQL
    MYSQL_HANDLE_UTC_OFFSET = Yes
    MYSQL_NAMED_CONNECTION = set-rds-user
    MYSQL_QUERY_FEATURE_TYPES_FOR_MERGE_FILTERS = Yes
    OUTPUT_FEATURES_DISPLAY = Schema and Data Features
    SQL_STATEMENT:
      update users.ukg_users
      set deactivated = NOW()
      where id = @Value(id)
Note: notify techops_automation of employee deactivations
HTTPCaller_3
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - Employee deactivated",
              "text": "Employee @Value(id) (@Value(first) @Value(last))",
              "color": "danger"
          }
          ]
      }
    UPLOAD_CONTENT_TYPE = Text (text/plain)
    UPLOAD_TYPE = Specify Upload Body
    USE_COOKIES = No
    VERIFY_SSL_CERTIFICATES = Yes

Bookmark: org
Note: Only process the most recent two files
Sampler_2
    RATE = 2
    SAMPLE_MODE = No
    SAMPLE_TYPE_LONG = First N Features
    SAMPLED -> Counter_2
Counter_2
    CNT_ATTR = _count
    DOMAIN = counter
    SCOPE = Local
    START = 0
    -> GoogleDriveConnector_3
    -> Logger_2
Note: download csv files
GoogleDriveConnector_3
    GOOGLEDRIVE_NAMED_CONNECTION = ellaine.chan Google Drive
    OPERATION_TYPE = Download
    PARAMETER_SETUP = _FME_FILES;@Value(_id);_FME_DATA_TARGET;Attribute;_FME_TARGET_FOLDER;<Unused>;_FME_INCLUDE_SUBFOLDERS;<Unused>;_FME_TARGET_ATTRIBUTE;_contents;FME_CONTROLLER_QUERY_FILE;transformers/dependencies/googledrive/Download.fme;FME_CONTROLLER_CHOICE;Download
    -> Tester_11
Tester_11
    BOOL_OP = OR
    TEST_CLAUSE = TEST @Value(_count) = 0
    TEST_MODE = TEST
    PASSED -> TempPathnameCreator_3
    FAILED -> TempPathnameCreator_4
TempPathnameCreator_3
    EXTENSION = .csv
    PATHNAME_ATTR = _pathname
    -> AttributeFileWriter_2
Note: latest version
AttributeFileWriter_2
    CHAR_ENCODING = fme-system
    FILE_NAME = @Value(_pathname)
    OVERWRITE_FILE = Overwrite file
    SOURCE_ATTR = _contents
    -> FeatureReader_2 [INITIATOR]
FeatureReader_2
    ATTRS_TO_EXPOSE = OL1 Code OL1 Name OL1 Manager Email OL2 Code OL2 Name OL2 Manager Email OL3 Code OL3 Name OL3 Alt Name Org Level 3 Manager's Email
    ATTR_ACCUM_MODE = Only Use Result
    COMBINE_GEOM = Use Result
    CSV2_CASE_SENSITIVE_FIELD_NAMES = Yes
    CSV2_CHUNK_SIZE = 100000
    CSV2_DATA_START_LINE = 2
    CSV2_DELIMITER = auto
    CSV2_ENCODING = UTF-8
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 10000
    CSV2_SCAN_TYPES = Yes
    CSV2_SKIP_DUPLICATE_DELIMITERS = No
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_USE_CUSTOM_SCHEMA = NO
    DATASET = @Value(_pathname)
    FORMAT = CSV2
    INTERACT = NONE
    OUTPUT_FEATURES_DISPLAY = Schema and Data Features
    <OTHER> -> AttributeManager_5
    <REJECTED> -> Terminator_2
AttributeManager_5
    ATTR_TABLE = SET_TO state = new
    -> Tester_4
    -> Tester_5
    -> Tester_3
TempPathnameCreator_4
    EXTENSION = .csv
    PATHNAME_ATTR = _pathname
    -> AttributeFileWriter_4
Note: older version
AttributeFileWriter_4
    CHAR_ENCODING = fme-system
    FILE_NAME = @Value(_pathname)
    OVERWRITE_FILE = Overwrite file
    SOURCE_ATTR = _contents
    -> FeatureReader_4 [INITIATOR]
FeatureReader_4
    ATTRS_TO_EXPOSE = OL1 Code OL1 Name OL1 Manager Email OL2 Code OL2 Name OL2 Manager Email OL3 Code OL3 Name OL3 Alt Name Org Level 3 Manager's Email
    ATTR_ACCUM_MODE = Only Use Result
    COMBINE_GEOM = Use Result
    CSV2_CASE_SENSITIVE_FIELD_NAMES = Yes
    CSV2_CHUNK_SIZE = 100000
    CSV2_DATA_START_LINE = 2
    CSV2_DELIMITER = auto
    CSV2_ENCODING = UTF-8
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 10000
    CSV2_SCAN_TYPES = Yes
    CSV2_SKIP_DUPLICATE_DELIMITERS = No
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_USE_CUSTOM_SCHEMA = NO
    DATASET = @Value(_pathname)
    FORMAT = CSV2
    INTERACT = NONE
    OUTPUT_FEATURES_DISPLAY = Schema and Data Features
    <OTHER> -> AttributeManager_6
    <REJECTED> -> Terminator_2
Terminator_2
    MESSAGE = Translation Terminated
AttributeManager_6
    ATTR_TABLE = SET_TO state = old
    -> Tester_3
    -> Tester_4
    -> Tester_5
Note: Process Org 1 columns
Tester_3
    BOOL_OP = OR
    TEST_CLAUSE = TEST OL1 Code ATTRIBUTE_HAS_A_VALUE ""
    TEST_MODE = TEST
    PASSED -> AttributeManager_2
Note: Process Org 2 columns
Tester_4
    BOOL_OP = OR
    TEST_CLAUSE = TEST OL2 Code ATTRIBUTE_HAS_A_VALUE ""
    TEST_MODE = TEST
    PASSED -> NullAttributeMapper_4
Note: If no manager value, use org1 manager
NullAttributeMapper_4
    ATTRCHOICE = Selected Attributes
    ATTRLIST = OL2 Manager Email
    NEW_VALUE = @Value(OL1 Manager Email)
    NULL_TREATMENT = New Value
    SOURCE_ATTR_VAL = Null
    -> AttributeManager_3
Note: Process Org 3 columns
Tester_5
    BOOL_OP = OR
    TEST_CLAUSE = TEST OL3 Code ATTRIBUTE_HAS_A_VALUE ""
    TEST_MODE = TEST
    PASSED -> NullAttributeMapper_5
Note: If no org 2 manager value, use org1 manager
NullAttributeMapper_5
    ATTRCHOICE = Selected Attributes
    ATTRLIST = OL2 Manager Email
    NEW_VALUE = @Value(OL1 Manager Email)
    NULL_TREATMENT = New Value
    SOURCE_ATTR_VAL = Null
    -> NullAttributeMapper_3
Note: If no org 3 manager value, use org2 manager
NullAttributeMapper_3
    ATTRCHOICE = Selected Attributes
    ATTRLIST = Org Level 3 Manager's Email
    NEW_VALUE = @Value(OL2 Manager Email)
    NULL_TREATMENT = New Value
    SOURCE_ATTR_VAL = Null
    -> AttributeManager_4
DuplicateFilter
    INPUT_ORDERED_CHOICE = No
    KEYATTR = id state
    UNIQUE -> FeatureMerger [REQUESTOR]
Logger_2
    LOG_FEATURE = LOG_ONLY
    MAXCOORDS = 20
    MAXFEATS = 20
    MESSAGE = Downloading... @Value(_name)
    SEVERITY = INFO
SQLCreator_3
    DATASET = set-rds-user
    EXPOSED_ATTRIBUTE_LIST = email,lead_id
    FORMAT = MYSQL
    MYSQL_HANDLE_UTC_OFFSET = Yes
    MYSQL_NAMED_CONNECTION = set-rds-user
    MYSQL_QUERY_FEATURE_TYPES_FOR_MERGE_FILTERS = Yes
    OUTPUT_FEATURES_DISPLAY = Schema and Data Features
    SQL_STATEMENT = SELECT email, id as lead_id from users.ukg_users
    RESULT -> FeatureMerger [SUPPLIER]
Note: merge in team lead ids
FeatureMerger
    ATTR_ACCUM_MODE = Merge Supplier
    ATTR_CONFLICT_RES = Use Requestor
    IGNORE_NULLS = No
    JOIN_KEYS = @ReplaceString(@Value(team_lead),"@safe.com","") @Value(email) AUTO
    MERGE_TYPE = Attributes Only
    PROCESS_DUPS = NO
    REJECT_NULL_MISSING_KEYS = No
    SUPPLIERS_FIRST = No
    MERGED -> SQLExecutor_3 [INITIATOR]
    MERGED -> Tester_12
    UNMERGED_REQUESTOR -> SQLExecutor_10 [INITIATOR]
    UNMERGED_REQUESTOR -> Tester_12
Tester_12
    BOOL_OP = OR
    TEST_CLAUSE = TEST @Value(state) = old
    TEST_MODE = TEST
    PASSED -> ChangeDetector_2 [ORIGINAL]
    FAILED -> ChangeDetector_2 [REVISED]
ChangeDetector_2
    BLANK_AND_MISSING_DIFFER = No
    BLANK_AND_MISSING_NAMES_TRAITS_DIFFER = No
    CHECK_COORDINATE_SYSTEMS = No
    CHECK_TYPES_AND_ENCODINGS = No
    LENIENT_MATCH = No
    MATCH = FULL
    MATCHATTRS = alt_name name parent_id team_lead
    MATCH_STRATEGY = Match Selected Attributes
    PREEMPTIVE_ATTRS = id
    UNCHANGED_OUTPUT = Output Original
    UPDATED_LIST_NAME = _org_change_list
    UPSERT_MODE = No
    UPDATED -> ListExploder_2
    INSERTED -> HTTPCaller_5
    DELETED -> SQLExecutor_5 [INITIATOR]
    DELETED -> HTTPCaller_6
    UNCHANGED -> TestFilter
ListExploder_2
    ATTR_ACCUM_MODE = Merge List Attributes
    ATTR_CONFLICT_RES = Use List Attribute Values
    INDEX_ATTR = _element_index
    LIST_ATTR = _org_change_list{}
    ELEMENTS -> NullAttributeMapper_2
NullAttributeMapper_2
    ATTRCHOICE = Selected Attributes
    ATTRLIST = originalValue revisedValue
    NEW_VALUE = Null
    NULL_TREATMENT = New Value
    SOURCE_ATTR_VAL = Null Empty "Missing (Selected Attributes Only)"
    -> HTTPCaller_2
Note: notify techops_automation of any changes
HTTPCaller_2
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - Team Updated",
              "text": "Team ID: @Value(id) (@Value(name))\nField: @Value(attributeName)\n@Value(originalValue) -> @Value(revisedValue)",
              "color": "warning"
          }
          ]
      }
    UPLOAD_CONTENT_TYPE = Text (text/plain)
    UPLOAD_TYPE = Specify Upload Body
    USE_COOKIES = No
    VERIFY_SSL_CERTIFICATES = Yes
SQLExecutor_5
    COMBINE_ATTRS = Result Attributes Only
    COMBINE_GEOM = Initiator Geometry Only
    DATASET = set-rds-user
    FORMAT = MYSQL
    MYSQL_HANDLE_UTC_OFFSET = Yes
    MYSQL_NAMED_CONNECTION = set-rds-user
    MYSQL_QUERY_FEATURE_TYPES_FOR_MERGE_FILTERS = Yes
    OUTPUT_FEATURES_DISPLAY = Schema and Data Features
    SQL_STATEMENT:
      UPDATE users.ukg_teams
      SET archived = NOW()
      WHERE id = "@Value(id)"
Note: notify techops_automation of new teams
HTTPCaller_5
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - Team Added",
              "text": "Team ID: @Value(id) (@Value(name))",
              "color": "good"
          }
          ]
      }
    UPLOAD_CONTENT_TYPE = Text (text/plain)
    UPLOAD_TYPE = Specify Upload Body
    USE_COOKIES = No
    VERIFY_SSL_CERTIFICATES = Yes
TestFilter
    DEFAULT_VALUE = <UNFILTERED>
    PASSED_TEST_GROUP_OUTPUT = FIRST
    TEST_LIST = "BOOL_OP,OR,COMPOSITE_TEST,""""""1"""""",TEST_CLAUSE,TEST @Value(org_level) = 1",@Value(org_level) = 1
    @Value(org_level) = 1 -> AttributeCreator_16
AttributeCreator_16
    ATTR_TABLE:
      SET_TO customfield_id = 11645
      SET_TO context_id = 11869
    -> HTTPCaller_25
Note: Add Division Name. / Disabled since fields are already created
HTTPCaller_25 [off]
    CONNECTION_TIMEOUT_LENGTH = 60
    CUSTOM_HEADERS = Authorization;Basic ZWxsYWluZS5jaGFuQHNhZmUuY29tOkFYZHF4VDRaSmZjdHV1dVRXUnF1QTRENw==
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://safesoftware.atlassian.net/rest/api/3/field/customfield_@Value(customfield_id)/context/@Value(context_id)/option
    TRANSFER_TIMEOUT_LENGTH = 90
    UPLOAD_BODY:
      {
          "options": [
              {
                  "disabled": false,
                  "value": "@Value(name)"
              }
          ]
      }
    UPLOAD_CONTENT_TYPE = JSON (application/json)
    UPLOAD_TYPE = Specify Upload Body
    USE_COOKIES = No
    VERIFY_SSL_CERTIFICATES = Yes
Note: notify techops_automation of team deactivations
HTTPCaller_6
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - Team Deactivated",
              "text": "Team ID: @Value(id) (@Value(name)) Notification to: <@U04HJ00CD>",
              "color": "danger"
          }
          ]
      }
    UPLOAD_CONTENT_TYPE = Text (text/plain)
    UPLOAD_TYPE = Specify Upload Body
    USE_COOKIES = No
    VERIFY_SSL_CERTIFICATES = Yes
Note: insert/update team with lead_id
SQLExecutor_3
    ATTR_IGNORE_NULLS = No
    COMBINE_ATTRS = Keep Initiator Attributes if Conflict
    COMBINE_GEOM = Initiator Geometry Only
    DATASET = set-rds-user
    FORMAT = MYSQL
    MYSQL_HANDLE_UTC_OFFSET = Yes
    MYSQL_NAMED_CONNECTION = set-rds-user
    MYSQL_QUERY_FEATURE_TYPES_FOR_MERGE_FILTERS = Yes
    OUTPUT_FEATURES_DISPLAY = Schema and Data Features
    SQL_STATEMENT:
      INSERT INTO users.ukg_teams (id, name, alt_name, parent_id, lead_id, last_update, org_level) VALUES("@Value(id)", "@Value(name)", "@Value(alt_name)", "@Value(parent_id)", @Value(lead_id), NOW(), @Value(org_level))
      ON DUPLICATE KEY UPDATE
      name = "@Value(name)", alt_name = "@Value(alt_name)", lead_id = @Value(lead_id), parent_id = "@Value(parent_id)", org_level = @Value(org_level), last_update=NOW();
Note: insert/update team with no lead_id
SQLExecutor_10
    ATTR_IGNORE_NULLS = No
    COMBINE_ATTRS = Keep Initiator Attributes if Conflict
    COMBINE_GEOM = Initiator Geometry Only
    DATASET = set-rds-user
    FORMAT = MYSQL
    MYSQL_HANDLE_UTC_OFFSET = Yes
    MYSQL_NAMED_CONNECTION = set-rds-user
    MYSQL_QUERY_FEATURE_TYPES_FOR_MERGE_FILTERS = Yes
    OUTPUT_FEATURES_DISPLAY = Schema and Data Features
    SQL_STATEMENT:
      INSERT INTO users.ukg_teams (id, name, alt_name, parent_id, last_update, org_level) VALUES("@Value(id)", "@Value(name)", "@Value(alt_name)", "@Value(parent_id)", NOW(), @Value(org_level))
      ON DUPLICATE KEY UPDATE
      name = "@Value(name)", alt_name = "@Value(alt_name)", parent_id = "@Value(parent_id)", last_update=NOW(), org_level = @Value(org_level);

Bookmark: Rename attributes t…e unused attributes
Note: Rename attributes to match ukg_org table col names, remove unused attributes, add org_level attribute
AttributeManager_2
    ATTR_TABLE:
      RENAME_SET_VALUE OL1 Code > id
      RENAME_SET_VALUE OL1 Name > name
      RENAME_SET_VALUE OL1 Manager Email > team_lead
      REMOVE OL2 Code
      REMOVE OL2 Name
      REMOVE OL2 Manager Email
      REMOVE OL3 Code
      REMOVE OL3 Name
      REMOVE OL3 Alt Name
      REMOVE Org Level 3 Manager's Email
      SET_TO org_level = 1
      SET_TO
    -> DuplicateFilter
AttributeManager_3
    ATTR_TABLE:
      RENAME_SET_VALUE OL1 Code > parent_id
      REMOVE OL1 Name
      REMOVE OL1 Manager Email
      RENAME_SET_VALUE OL2 Code > id
      RENAME_SET_VALUE OL2 Name > name
      RENAME_SET_VALUE OL2 Manager Email > team_lead
      REMOVE OL3 Code
      REMOVE OL3 Name
      REMOVE OL3 Alt Name
      REMOVE Org Level 3 Manager's Email
      SET_TO org_level = 2
    -> DuplicateFilter
AttributeManager_4
    ATTR_TABLE:
      REMOVE OL1 Code
      REMOVE OL1 Name
      REMOVE OL1 Manager Email
      RENAME_SET_VALUE OL2 Code > parent_id
      REMOVE OL2 Name
      REMOVE OL2 Manager Email
      RENAME_SET_VALUE OL3 Code > id
      RENAME_SET_VALUE OL3 Name > name
      RENAME_SET_VALUE OL3 Alt Name > alt_name
      RENAME_SET_VALUE Org Level 3 Manager's Email > team_lead
      SET_TO org_level = 3
    -> DuplicateFilter

Bookmark: Generate gtb-1_usernames
SQLCreator_4
    DATASET = set-rds-user
    EXPOSED_ATTRIBUTE_LIST = first,last,preferred_first_name,email,title,team_id,slack_id,work_extension,ldap,office_number,office_floor,former_coop,deactivated,changelog_reviewer,guide_admin,guide_component_ownership_admin,avatar_url,jira_avatar,code_signature,gtb-1_username,netsuite_employee_id,netsuite_vendor_id,netsuite_employee_id_sb,netsuite_vendor_id_sb,netsuite_admin,id,name,lead_id,parent_id,alt_name,development,last_update,archived,org_level,netsuite_id,netsuite_id_sb
    FORMAT = MYSQL
    MYSQL_HANDLE_UTC_OFFSET = Yes
    MYSQL_NAMED_CONNECTION = set-rds-user
    MYSQL_QUERY_FEATURE_TYPES_FOR_MERGE_FILTERS = Yes
    OUTPUT_FEATURES_DISPLAY = Schema and Data Features
    SQL_STATEMENT:
      SELECT u.*, t.development FROM users.ukg_users as u
      left join users.ukg_teams as t on u.team_id = t.id
    RESULT -> AttributeCreator_3
Note: create display name, default to preferred first name
AttributeCreator_3
    ATTR_TABLE = SET_TO display_name = @Value(preferred_first_name)
    -> NullAttributeMapper_7
Note: use first name as display name if null
NullAttributeMapper_7
    ATTRCHOICE = Selected Attributes
    ATTRLIST = display_name
    NEW_VALUE = @Value(first)
    NULL_TREATMENT = New Value
    SOURCE_ATTR_VAL = Null Empty "Missing (Selected Attributes Only)"
    -> Tester_20
Note: gtb-1 username missing?
Tester_20
    BOOL_OP = AND
    TEST_CLAUSE:
      TEST gtb-1_username ATTRIBUTE_VALUE_NULL ""
      TEST deactivated ATTRIBUTE_VALUE_NULL ""
      TEST @Value(development) = 1
    TEST_MODE = TEST
    PASSED -> AttributeCreator_15
Note: create gtb-1_username
AttributeCreator_15
    ATTR_TABLE = SET_TO gtb-1 = @LowerCase(@ReplaceString(@Value(display_name)," ","-",caseSensitive=TRUE))-@LowerCase(@Value(last))
    -> SQLExecutor_9 [INITIATOR]
Note: save gtb-1 username
SQLExecutor_9
    ATTR_IGNORE_NULLS = Yes
    COMBINE_ATTRS = Keep Initiator Attributes if Conflict
    COMBINE_GEOM = Initiator Geometry Only
    DATASET = set-rds-user
    EXPOSED_ATTRIBUTE_LIST = revised_team_name,revised_alt_name
    FORMAT = MYSQL
    MYSQL_HANDLE_UTC_OFFSET = Yes
    MYSQL_NAMED_CONNECTION = set-rds-user
    MYSQL_QUERY_FEATURE_TYPES_FOR_MERGE_FILTERS = Yes
    OUTPUT_FEATURES_DISPLAY = Schema and Data Features
    SQL_STATEMENT:
      update users.ukg_users
      set `gtb-1_username` = "@Value(gtb-1)"
      where id = @Value(id) limit 1
