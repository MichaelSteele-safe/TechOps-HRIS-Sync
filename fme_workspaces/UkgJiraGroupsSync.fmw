FME workspace UkgJiraGroupsSync.fmw

Parameters:
- SLACK_NOTIFICATION_WEBHOOK = https://hooks.slack.com/services/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   # webhook to send notification to slack
- DestDataset_MYSQL_DB = set-rds   # (MySQL compatible) Connection
- DestDataset_MYSQL_DB_5 = set-rds   # (MySQL compatible) Connection
- DestDataset_MYSQL_DB_7 = set-rds   # (MySQL compatible) Connection
- DestDataset_MYSQL_DB_6 = set-rds   # (MySQL compatible) Connection

Writers:
- CSV2_1: CSV2 to /Users/ellaine.chan/Desktop
- MYSQL_DB_1: MYSQL_DB to $(DestDataset_MYSQL_DB)
- MYSQL_DB_2: MYSQL_DB to $(DestDataset_MYSQL_DB_5)
- MYSQL_DB_3: MYSQL_DB to $(DestDataset_MYSQL_DB_7)
- MYSQL_DB_4: MYSQL_DB to $(DestDataset_MYSQL_DB_6)

Note: UKG Generated reports are sent to hrisautomation@safe.com, picked up by Google App Scripts and dropped to Google Drive. This workspace reads the latest CSV files to migrate data into our database. / Author: Ellaine Chan

Bookmark: Get UKG Report
Creator
    GEOMTYPE = Geometry Object
    NUM = 1
    CREATED -> GoogleDriveConnector
Note: List all files in the drive
GoogleDriveConnector
    GOOGLEDRIVE_NAMED_CONNECTION = ellaine.chan Google Drive
    OPERATION_TYPE = List
    PARAMETER_SETUP = _FME_FILES;1rjRm_CFXUfnNy3VOpvD_QQaHeIFgCVpN;_FME_INCLUDE_SUBFOLDERS;Yes;_FME_OBJECT_NAME_ATTRIBUTE;_name;_FME_OBJECT_ID_ATTRIBUTE;_id;_FME_OBJECT_PATH_ATTRIBUTE;_sharable_link;_FME_OBJECT_SIZE_ATTRIBUTE;_file_size;_FME_OBJECT_MODIFIED_ATTRIBUTE;_file_last_modified;_FME_OBJECT_TYPE_ATTRIBUTE;_file_or_folder;_FME_OBJECT_RELATIVE_PATH_ATTRIBUTE;_relative_path;FME_CONTROLLER_QUERY_FILE;transformers/dependencies/googledrive/List.fme;FME_CONTROLLER_CHOICE;List
    -> Sorter
Note: sort by date
Sorter
    SORT_PARM = _file_last_modified NATURAL DESCENDING
    SORTED -> Tester
Tester
    BOOL_OP = OR
    TEST_CLAUSE = CASE_INSENSITIVE_TEST @Value(_name) CONTAINS Employee
    TEST_MODE = CASE_INSENSITIVE_TEST
    PASSED -> Sampler
    FAILED -> Sampler_2
Note: Only process the latest employee file
Sampler
    RATE = 1
    SAMPLE_MODE = No
    SAMPLE_TYPE_LONG = First N Features
    SAMPLED -> GoogleDriveConnector_2
Note: download latest two employee csv
GoogleDriveConnector_2
    GOOGLEDRIVE_NAMED_CONNECTION = ellaine.chan Google Drive
    OPERATION_TYPE = Download
    PARAMETER_SETUP = _FME_FILES;@Value(_id);_FME_DATA_TARGET;Attribute;_FME_TARGET_FOLDER;<Unused>;_FME_INCLUDE_SUBFOLDERS;<Unused>;_FME_TARGET_ATTRIBUTE;_contents;FME_CONTROLLER_QUERY_FILE;transformers/dependencies/googledrive/Download.fme;FME_CONTROLLER_CHOICE;Download
    -> TempPathnameCreator
    <REJECTED> -> TempPathnameCreator
TempPathnameCreator
    EXTENSION = .csv
    PATHNAME_ATTR = _pathname
    -> AttributeFileWriter
Note: latest version
AttributeFileWriter
    CHAR_ENCODING = fme-system
    FILE_NAME = @Value(_pathname)
    OVERWRITE_FILE = Overwrite file
    SOURCE_ATTR = _contents
    -> FeatureReader_5 [INITIATOR]
FeatureReader_5
    ATTRS_TO_EXPOSE = Last Name First Name Preferred First Name Employee Number Employee Email Job Org Level 2 Code Org Level 2 Org Level 3 Code OL3 Alt Org Level 3 Work Extension Slack ID AD Login Office Number Office Floor Former Co-op OL2 Alt Org Level 1 Org Level 1 Code
    ATTR_ACCUM_MODE = Only Use Result
    COMBINE_GEOM = Use Result
    CSV2_CASE_SENSITIVE_FIELD_NAMES = Yes
    CSV2_CHUNK_SIZE = 100000
    CSV2_DATA_START_LINE = 2
    CSV2_DATE_INPUT_FORMAT = ISO
    CSV2_DELIMITER = auto
    CSV2_ENCODING = UTF-8
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 10000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = YES
    DATASET = @Value(_pathname)
    FORMAT = CSV2
    INTERACT = NONE
    OUTPUT_FEATURES_DISPLAY = Schema and Data Features
    <OTHER> -> AttributeCreator_8
AttributeCreator_8
    ATTR_TABLE:
      SET_TO display_name = @Value(Preferred First Name)
      SET_TO team_lead = 0
      SET_TO information_services_team_lead = 0
      SET_TO marketing_team_lead = 0
    -> FeatureMerger [REQUESTOR]
Note: Only process the latest org file
Sampler_2
    RATE = 1
    SAMPLE_MODE = No
    SAMPLE_TYPE_LONG = First N Features
    SAMPLED -> GoogleDriveConnector_3
Note: download latest two employee csv
GoogleDriveConnector_3
    GOOGLEDRIVE_NAMED_CONNECTION = ellaine.chan Google Drive
    OPERATION_TYPE = Download
    PARAMETER_SETUP = _FME_FILES;@Value(_id);_FME_DATA_TARGET;Attribute;_FME_TARGET_FOLDER;<Unused>;_FME_INCLUDE_SUBFOLDERS;<Unused>;_FME_TARGET_ATTRIBUTE;_contents;FME_CONTROLLER_QUERY_FILE;transformers/dependencies/googledrive/Download.fme;FME_CONTROLLER_CHOICE;Download
    -> TempPathnameCreator_2
TempPathnameCreator_2
    EXTENSION = .csv
    PATHNAME_ATTR = _pathname
    -> AttributeFileWriter_2
Note: latest version
AttributeFileWriter_2
    CHAR_ENCODING = fme-system
    FILE_NAME = @Value(_pathname)
    OVERWRITE_FILE = Overwrite file
    SOURCE_ATTR = _contents
    -> FeatureReader_2 [INITIATOR]

Bookmark: Determine team leads
Note: Get team leads
FeatureReader_2
    ATTRS_TO_EXPOSE = OL1 Manager Email OL2 Manager Email Org Level 3 Manager's Email
    ATTR_ACCUM_MODE = Only Use Result
    COMBINE_GEOM = Use Result
    CSV2_CASE_SENSITIVE_FIELD_NAMES = Yes
    CSV2_CHUNK_SIZE = 100000
    CSV2_DATA_START_LINE = 2
    CSV2_DELIMITER = auto
    CSV2_ENCODING = UTF-8
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 10000
    CSV2_SCAN_TYPES = Yes
    CSV2_SKIP_DUPLICATE_DELIMITERS = No
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_USE_CUSTOM_SCHEMA = YES
    DATASET = @Value(_pathname)
    FORMAT = CSV2
    INTERACT = NONE
    OUTPUT_FEATURES_DISPLAY = Schema and Data Features
    <OTHER> -> DuplicateFilter
    <OTHER> -> DuplicateFilter_3
    <OTHER> -> DuplicateFilter_4
DuplicateFilter
    INPUT_ORDERED_CHOICE = No
    KEYATTR = OL1 Manager Email
    UNIQUE -> FeatureMerger [SUPPLIER]
FeatureMerger
    ATTR_ACCUM_MODE = Merge Supplier
    ATTR_CONFLICT_RES = Use Requestor
    IGNORE_NULLS = No
    JOIN_KEYS = @Value(Employee Email) @Value(OL1 Manager Email) AUTO
    MERGE_TYPE = Attributes Only
    PROCESS_DUPS = NO
    REJECT_NULL_MISSING_KEYS = No
    SUPPLIERS_FIRST = No
    MERGED -> AttributeManager
    UNMERGED_REQUESTOR -> FeatureMerger_2 [REQUESTOR]
DuplicateFilter_3
    INPUT_ORDERED_CHOICE = No
    KEYATTR = OL2 Manager Email
    UNIQUE -> FeatureMerger_2 [SUPPLIER]
FeatureMerger_2
    ATTR_ACCUM_MODE = Merge Supplier
    ATTR_CONFLICT_RES = Use Requestor
    IGNORE_NULLS = No
    JOIN_KEYS = @Value(Employee Email) @Value(OL2 Manager Email) AUTO
    MERGE_TYPE = Attributes Only
    PROCESS_DUPS = NO
    REJECT_NULL_MISSING_KEYS = No
    SUPPLIERS_FIRST = No
    MERGED -> AttributeManager
    UNMERGED_REQUESTOR -> FeatureMerger_3 [REQUESTOR]
DuplicateFilter_4
    INPUT_ORDERED_CHOICE = No
    KEYATTR = Org Level 3 Manager's Email
    UNIQUE -> FeatureMerger_3 [SUPPLIER]
FeatureMerger_3
    ATTR_ACCUM_MODE = Merge Supplier
    ATTR_CONFLICT_RES = Use Requestor
    IGNORE_NULLS = No
    JOIN_KEYS = @Value(Employee Email) @Value(Org Level 3 Manager's Email) AUTO
    MERGE_TYPE = Attributes Only
    PROCESS_DUPS = NO
    REJECT_NULL_MISSING_KEYS = No
    SUPPLIERS_FIRST = No
    MERGED -> AttributeManager
    UNMERGED_REQUESTOR -> NullAttributeMapper_9
Note: set team lead to 1
AttributeManager
    ATTR_TABLE = SET_TO team_lead = 1
    -> TestFilter
TestFilter
    DEFAULT_VALUE = <UNFILTERED>
    PASSED_TEST_GROUP_OUTPUT = FIRST
    TEST_LIST = "BOOL_OP,OR,COMPOSITE_TEST,""""""1"""""",TEST_CLAUSE,TEST @Value(Org Level 1 Code) = MK0000",Marketing TL,"BOOL_OP,OR,COMPOSITE_TEST,""""""1"""""",TEST_CLAUSE,TEST @Value(Org Level 1 Code) = IS0000",IS TL
    <UNFILTERED> -> NullAttributeMapper_9
    IS TL -> AttributeManager_3
    Marketing TL -> AttributeManager_2
AttributeManager_2
    ATTR_TABLE = SET_TO marketing_team_lead = 1
    -> NullAttributeMapper_9
AttributeManager_3
    ATTR_TABLE = SET_TO information_services_team_lead = 1
    -> NullAttributeMapper_9

Bookmark: Update Jira Group
Note: use first name as display name if null
NullAttributeMapper_9
    ATTRCHOICE = Selected Attributes
    ATTRLIST = display_name
    NEW_VALUE = @Value(First Name)
    NULL_TREATMENT = New Value
    SOURCE_ATTR_VAL = Null Empty "Missing (Selected Attributes Only)"
    -> Tester_16
Note: Only try to get alt_name if org3 exists
Tester_16
    BOOL_OP = OR
    TEST_CLAUSE = TEST Org Level 3 Code ATTRIBUTE_HAS_A_VALUE ""
    TEST_MODE = TEST
    PASSED -> SQLExecutor_8 [INITIATOR]
    FAILED -> AttributeCreator_9
Note: get alt_name
SQLExecutor_8
    ATTR_IGNORE_NULLS = Yes
    COMBINE_ATTRS = Keep Result Attributes if Conflict
    COMBINE_GEOM = Initiator Geometry Only
    DATASET = set-rds-user
    EXPOSED_ATTRIBUTE_LIST = alt_name
    FORMAT = MYSQL
    MYSQL_HANDLE_UTC_OFFSET = Yes
    MYSQL_NAMED_CONNECTION = set-rds-user
    MYSQL_QUERY_FEATURE_TYPES_FOR_MERGE_FILTERS = Yes
    OUTPUT_FEATURES_DISPLAY = Schema and Data Features
    SQL_STATEMENT = select alt_name from users.ukg_teams where id = "@Value(Org Level 3 Code)"
    RESULT -> HTTPCaller_8
AttributeCreator_9
    ATTR_TABLE = SET_TO alt_name
    -> HTTPCaller_8
Note: get accountId
HTTPCaller_8
    CONNECTION_TIMEOUT_LENGTH = 60
    CUSTOM_HEADERS = Authorization;Basic amlyYWFwaUBzYWZlLmNvbTpZN3lwbkZha2g1V1BPVUhSbkJPUTVEQjE=
    ERROR_ATTR = _error
    FOLLOW_REDIRECTS = FOLLOW_WITH_GET
    HTTP_METHOD = GET
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _user_response_body
    TARGET_ATTR_ENCODING = auto-detect
    TARGET_URL = https://safesoftware.atlassian.net/rest/api/3/user/search?query=@Value(Employee Email)
    TRANSFER_TIMEOUT_LENGTH = 90
    USE_COOKIES = No
    VERIFY_SSL_CERTIFICATES = Yes
    -> JSONExtractor
Note: extract accountId and jira_avatar
JSONExtractor
    EXTRACT_QUERY_TABLE = accountId json[*]["accountId"] jira_avatar json[*]["avatarUrls"]["48x48"]
    JSON_DOCUMENT = @Value(_user_response_body)
    READ_FROM_FILE = NO
    EVALUATED -> Tester_17
Tester_17
    BOOL_OP = OR
    TEST_CLAUSE = TEST accountId ATTRIBUTE_HAS_A_VALUE ""
    TEST_MODE = TEST
    PASSED -> HTTPCaller_9
Note: get groups that user is in
HTTPCaller_9
    CONNECTION_TIMEOUT_LENGTH = 60
    CUSTOM_HEADERS = Authorization;Basic amlyYWFwaUBzYWZlLmNvbTpZN3lwbkZha2g1V1BPVUhSbkJPUTVEQjE=
    ERROR_ATTR = _error
    FOLLOW_REDIRECTS = FOLLOW_WITH_GET
    HTTP_METHOD = GET
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _user_group_response_body
    TARGET_ATTR_ENCODING = auto-detect
    TARGET_URL = https://safesoftware.atlassian.net/rest/api/3/user?accountId=@Value(accountId)&expand=groups
    TRANSFER_TIMEOUT_LENGTH = 90
    USE_COOKIES = No
    VERIFY_SSL_CERTIFICATES = Yes
    -> AttributeCreator_4
AttributeCreator_4
    ATTR_TABLE:
      SET_TO group_operation
      SET_TO jira_group
    -> PythonCaller
    -> PythonCaller_5
    -> PythonCaller_2
    -> PythonCaller_3
    -> PythonCaller_4
Note: Maintain group-customer-support
PythonCaller_5
    PYTHONSOURCE:
      import fme
      import fmeobjects
      import json


      class FeatureProcessor(object):
          """Template Class Interface:
          When using this class, make sure its name is set as the value of the 'Class
          to Process Features' transformer parameter.
          """

          def __init__(self):
              """Base constructor for class members."""
              pass

          def input(self, feature):
              user_group_name_list = []
              customer_success_group = "group-customer-support"
              user_groups_list = json.loads(feature.getAttribute('_user_group_response_body'))["groups"]["items"]
              in_customer_success_group = False
              if feature.getAttribute('Org Level 2 Code') == "CS3000" and feature.getAttribute('Org Level 3 Code') != "CS3120" and feature.getAttribute('Org Level 3 Code') != "CS3140":
                  in_customer_success_group = True
              for group in user_groups_list:
                  user_group_name_list.append(group["name"])
                  if in_customer_success_group == False and group["name"] == customer_success_group:
                      new_feature = feature.clone()
                      new_feature.setAttribute('group_operation', 'delete')
                      new_feature.setAttribute('jira_group', customer_success_group)
                      self.pyoutput(new_feature)
              if in_customer_success_group and customer_success_group not in user_group_name_list:
                  new_feature = feature.clone()
                  new_feature.setAttribute('group_operation', 'add')
                  new_feature.setAttribute('jira_group', customer_success_group)
                  self.pyoutput(new_feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> HTTPCaller_13
Note: Maintain group-team-lead
PythonCaller_2
    PYTHONSOURCE:
      import fme
      import fmeobjects
      import json


      class FeatureProcessor(object):
          """Template Class Interface:
          When using this class, make sure its name is set as the value of the 'Class
          to Process Features' transformer parameter.
          """

          def __init__(self):
              """Base constructor for class members."""
              pass

          def input(self, feature):
              user_group_name_list = []
              teamlead_group = "group-teamleads"
              user_groups_list = json.loads(feature.getAttribute('_user_group_response_body'))["groups"]["items"]
              in_team_lead_group = False
              if feature.getAttribute('team_lead') == 1:
                  in_team_lead_group = True
              for group in user_groups_list:
                  user_group_name_list.append(group["name"])
                  if in_team_lead_group == False and group["name"] == teamlead_group:
                      new_feature = feature.clone()
                      new_feature.setAttribute('group_operation', 'delete')
                      new_feature.setAttribute('jira_group', teamlead_group)
                      self.pyoutput(new_feature)
              if in_team_lead_group and teamlead_group not in user_group_name_list:
                  new_feature = feature.clone()
                  new_feature.setAttribute('group_operation', 'add')
                  new_feature.setAttribute('jira_group', teamlead_group)
                  self.pyoutput(new_feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> HTTPCaller_13
Note: Maintain group-infosrvcs-leads
PythonCaller_3
    PYTHONSOURCE:
      import fme
      import fmeobjects
      import json


      class FeatureProcessor(object):
          """Template Class Interface:
          When using this class, make sure its name is set as the value of the 'Class
          to Process Features' transformer parameter.
          """

          def __init__(self):
              """Base constructor for class members."""
              pass

          def input(self, feature):
              user_group_name_list = []
              teamlead_group = "group-infosrvcs-leads"
              user_groups_list = json.loads(feature.getAttribute('_user_group_response_body'))["groups"]["items"]
              in_team_lead_group = False
              if feature.getAttribute('information_services_team_lead') == 1:
                  in_team_lead_group = True
              for group in user_groups_list:
                  user_group_name_list.append(group["name"])
                  if in_team_lead_group == False and group["name"] == teamlead_group:
                      new_feature = feature.clone()
                      new_feature.setAttribute('group_operation', 'delete')
                      new_feature.setAttribute('jira_group', teamlead_group)
                      self.pyoutput(new_feature)
              if in_team_lead_group and teamlead_group not in user_group_name_list:
                  new_feature = feature.clone()
                  new_feature.setAttribute('group_operation', 'add')
                  new_feature.setAttribute('jira_group', teamlead_group)
                  self.pyoutput(new_feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> HTTPCaller_13
Note: Maintain group-marketing-leads
PythonCaller_4
    PYTHONSOURCE:
      import fme
      import fmeobjects
      import json


      class FeatureProcessor(object):
          """Template Class Interface:
          When using this class, make sure its name is set as the value of the 'Class
          to Process Features' transformer parameter.
          """

          def __init__(self):
              """Base constructor for class members."""
              pass

          def input(self, feature):
              user_group_name_list = []
              teamlead_group = "group-marketing-leads"
              user_groups_list = json.loads(feature.getAttribute('_user_group_response_body'))["groups"]["items"]
              in_team_lead_group = False
              if feature.getAttribute('marketing_team_lead') == 1:
                  in_team_lead_group = True
              for group in user_groups_list:
                  user_group_name_list.append(group["name"])
                  if in_team_lead_group == False and group["name"] == teamlead_group:
                      new_feature = feature.clone()
                      new_feature.setAttribute('group_operation', 'delete')
                      new_feature.setAttribute('jira_group', teamlead_group)
                      self.pyoutput(new_feature)
              if in_team_lead_group and teamlead_group not in user_group_name_list:
                  new_feature = feature.clone()
                  new_feature.setAttribute('group_operation', 'add')
                  new_feature.setAttribute('jira_group', teamlead_group)
                  self.pyoutput(new_feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> HTTPCaller_13
Note: Determine which groups user needs to be added or removed from and output as new feature
PythonCaller
    PYTHONSOURCE:
      import fme
      import fmeobjects
      import json


      class FeatureProcessor(object):
          """Template Class Interface:
          When using this class, make sure its name is set as the value of the 'Class
          to Process Features' transformer parameter.
          """

          def __init__(self):
              """Base constructor for class members."""
              pass


          def input(self, feature):
              user_groups_list = json.loads(feature.getAttribute('_user_group_response_body'))["groups"]["items"]
              user_group_name_list = []
              org3_jira_name = ""
              org2_jira_name = ""
              org1_jira_name = org1_jira_name =  "team-" + feature.getAttribute('Org Level 1').replace("- ", "" ).replace(" ", "-" ).lower()
              if feature.getAttribute('OL3 Alt') == None or len(feature.getAttribute('OL3 Alt')) == 0:
                  org3_jira_name =  "team-" + feature.getAttribute('Org Level 3').replace("- ", "" ).replace(" ", "-" ).lower()
              else:
                  org3_jira_name =  "team-" + feature.getAttribute('OL3 Alt').replace("- ", "" ).replace(" ", "-" ).lower()
              if feature.getAttribute('OL2 Alt') == None or len(feature.getAttribute('OL2 Alt')) == 0:
                  org2_jira_name =  "team-" + feature.getAttribute('Org Level 2').replace("- ", "" ).replace(" ", "-" ).lower()
              else:
                  org2_jira_name =  "team-" + feature.getAttribute('OL2 Alt').replace("- ", "" ).replace(" ", "-" ).lower()
              print(feature.getAttribute('display_name'))
              print(org3_jira_name)
              print(org2_jira_name)
              print(org1_jira_name)
              for group in user_groups_list:
                  print("group: %s" % group["name"])
                  user_group_name_list.append(group["name"])
                  # don't remove PMs from their dev team
                  org3_name =  feature.getAttribute('Org Level 3').replace("Product Mgmt", "Product Management")
                  if group["name"] != org1_jira_name and group["name"] != org2_jira_name and group["name"] != org3_jira_name and group["name"].find("team") ==0:
                      if "Product Management" in org3_name:
                          dev_team = org3_name.replace("Product Management", "").rstrip().lower()
                          if dev_team not in group["name"]:
                              new_feature = feature.clone()
                              new_feature.setAttribute('group_operation', 'delete')
                              new_feature.setAttribute('jira_group', group["name"])
                              self.pyoutput(new_feature)
                      else:
                          new_feature = feature.clone()
                          new_feature.setAttribute('group_operation', 'delete')
                          new_feature.setAttribute('jira_group', group["name"])
                          self.pyoutput(new_feature)
              if not org1_jira_name in user_group_name_list:
                  new_feature = feature.clone()
                  new_feature.setAttribute('group_operation', 'add')
                  new_feature.setAttribute('jira_group', org1_jira_name)
                  self.pyoutput(new_feature)
              if not org2_jira_name in user_group_name_list:
                  new_feature = feature.clone()
                  new_feature.setAttribute('group_operation', 'add')
                  new_feature.setAttribute('jira_group', org2_jira_name)
                  self.pyoutput(new_feature)
              if not org3_jira_name in user_group_name_list:
                  if feature.getAttribute('Org Level 3 Code') != None and len(feature.getAttribute('Org Level 3')) > 1:
                      new_feature = feature.clone()
                      new_feature.setAttribute('group_operation', 'add')
                      new_feature.setAttribute('jira_group', org3_jira_name)
                      self.pyoutput(new_feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> HTTPCaller_13
Note: get groupId
HTTPCaller_13
    CONNECTION_TIMEOUT_LENGTH = 60
    CUSTOM_HEADERS = Authorization;Basic amlyYWFwaUBzYWZlLmNvbTpZN3lwbkZha2g1V1BPVUhSbkJPUTVEQjE=
    ERROR_ATTR = _error
    FOLLOW_REDIRECTS = FOLLOW_WITH_GET
    HTTP_METHOD = GET
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _jira_group_response_body
    TARGET_ATTR_ENCODING = auto-detect
    TARGET_URL = https://safesoftware.atlassian.net/rest/api/3/groups/picker?query=@Value(jira_group)
    TRANSFER_TIMEOUT_LENGTH = 90
    USE_COOKIES = No
    VERIFY_SSL_CERTIFICATES = Yes
    -> JSONExtractor_2
Note: extract groupId
JSONExtractor_2
    EXTRACT_QUERY_TABLE = groupId json["groups"][0]["groupId"] groupName json["groups"][0]["name"]
    JSON_DOCUMENT = @Value(_jira_group_response_body)
    READ_FROM_FILE = NO
    EVALUATED -> Tester_10
Tester_10
    BOOL_OP = OR
    TEST_CLAUSE = TEST @Value(group_operation) = add
    TEST_MODE = TEST
    PASSED -> Tester_15
    FAILED -> Tester_13
Note: does group already exist?
Tester_15
    BOOL_OP = AND
    TEST_CLAUSE:
      TEST groupId ATTRIBUTE_HAS_A_VALUE ""
      TEST @Value(groupName) = @Value(jira_group)
    TEST_MODE = TEST
    PASSED -> AttributeCreator_11
    FAILED -> DuplicateFilter_2
DuplicateFilter_2
    INPUT_ORDERED_CHOICE = No
    KEYATTR = jira_group
    UNIQUE -> HTTPCaller_14
    DUPLICATE -> FeatureJoiner [RIGHT]
Note: create jira group
HTTPCaller_14
    CONNECTION_TIMEOUT_LENGTH = 60
    CUSTOM_HEADERS = Authorization;Basic ZWxsYWluZS5jaGFuQHNhZmUuY29tOkFYZHF4VDRaSmZjdHV1dVRXUnF1QTRENw==
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _new_group_response_body
    TARGET_ATTR_ENCODING = auto-detect
    TARGET_URL = https://safesoftware.atlassian.net/rest/api/3/group
    TRANSFER_TIMEOUT_LENGTH = 90
    UPLOAD_BODY:
      {
          "name": "@Value(jira_group)"
      }
    UPLOAD_CONTENT_TYPE = JSON (application/json)
    UPLOAD_TYPE = Specify Upload Body
    USE_COOKIES = No
    VERIFY_SSL_CERTIFICATES = Yes
    -> JSONExtractor_3
Note: extract groupId
JSONExtractor_3
    EXTRACT_QUERY_TABLE = groupId json["groupId"]
    JSON_DOCUMENT = @Value(_new_group_response_body)
    READ_FROM_FILE = NO
    EVALUATED -> HTTPCaller_11
    EVALUATED -> AttributeCreator_11
    EVALUATED -> AttributeKeeper
Note: notify techops_automation jira group was created
HTTPCaller_11
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - Created Jira Group",
              "text": "@Value(jira_group)",
              "color": "good"
          }
          ]
      }
    UPLOAD_CONTENT_TYPE = Text (text/plain)
    UPLOAD_TYPE = Specify Upload Body
    USE_COOKIES = No
    VERIFY_SSL_CERTIFICATES = Yes
AttributeKeeper
    CREATE_BULK_MODE_FEATURES = NO
    KEEP_ATTRS = groupId,jira_group
    -> FeatureJoiner [LEFT]
FeatureJoiner
    ATTR_CONFLICT_RES = Prefer Left
    GEOMETRY_HANDLING = Prefer Left
    JOIN_KEYS = jira_group jira_group AUTO
    JOIN_MODE = Left
    JOINED -> AttributeCreator_11
AttributeCreator_11
    ATTR_TABLE:
      SET_TO add_url = https://safesoftware.atlassian.net/rest/api/3/group/user?groupId=@Value(groupId)
      SET_TO url_body = {
            "accountId": "@Value(accountId)"
        }
    -> HTTPCaller_16
Note: add user to jira group
HTTPCaller_16
    CONNECTION_TIMEOUT_LENGTH = 60
    CUSTOM_HEADERS = Authorization;Basic ZWxsYWluZS5jaGFuQHNhZmUuY29tOkFYZHF4VDRaSmZjdHV1dVRXUnF1QTRENw==
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _new_group_response_body
    TARGET_ATTR_ENCODING = auto-detect
    TARGET_URL = https://safesoftware.atlassian.net/rest/api/3/group/user?groupId=@Value(groupId)
    TRANSFER_TIMEOUT_LENGTH = 90
    UPLOAD_BODY:
      {
          "accountId": "@Value(accountId)"
      }
    UPLOAD_CONTENT_TYPE = JSON (application/json)
    UPLOAD_TYPE = Specify Upload Body
    USE_COOKIES = No
    VERIFY_SSL_CERTIFICATES = Yes
    -> HTTPCaller_12
Note: notify techops_automation user was added to group
HTTPCaller_12
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - User added to Jira Group",
              "text": "Employee @Value(display_name) @Value(Last Name) was added to @Value(jira_group)",
              "color": "good"
          }
          ]
      }
    UPLOAD_CONTENT_TYPE = Text (text/plain)
    UPLOAD_TYPE = Specify Upload Body
    USE_COOKIES = No
    VERIFY_SSL_CERTIFICATES = Yes
Note: EXCEPTIONS
Tester_13
    BOOL_OP = OR
    TEST_CLAUSE:
      TEST @Value(jira_group) = team-facilities
      CASE_INSENSITIVE_TEST john.leesbonnie.alexander CONTAINS @Value(Employee Email)
    TEST_MODE = PER_TEST
    FAILED -> AttributeCreator_10
AttributeCreator_10
    ATTR_TABLE = SET_TO delete_url = https://safesoftware.atlassian.net/rest/api/3/group/user?groupId=@Value(groupId)&accountId=@Value(accountId)
    -> HTTPCaller_18
Note: remove user from group
HTTPCaller_18
    CONNECTION_TIMEOUT_LENGTH = 60
    CUSTOM_HEADERS = Authorization;Basic ZWxsYWluZS5jaGFuQHNhZmUuY29tOkFYZHF4VDRaSmZjdHV1dVRXUnF1QTRENw==
    ERROR_ATTR = _error
    FOLLOW_REDIRECTS = FOLLOW_WITH_GET
    HTTP_METHOD = DELETE
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _remove_user_from_group_response_body
    TARGET_ATTR_ENCODING = auto-detect
    TARGET_URL = https://safesoftware.atlassian.net/rest/api/3/group/user?groupId=@Value(groupId)&accountId=@Value(accountId)
    TRANSFER_TIMEOUT_LENGTH = 90
    UPLOAD_BODY:
      {
          "accountId": "@Value(accountId)"
      }
    UPLOAD_CONTENT_TYPE = JSON (application/json)
    UPLOAD_TYPE = Specify Upload Body
    USE_COOKIES = No
    VERIFY_SSL_CERTIFICATES = Yes
    -> HTTPCaller_10
Note: notify techops_automation of removed from jira group
HTTPCaller_10
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - User removed from Jira Group",
              "text": "Employee @Value(display_name) @Value(Last Name) was removed from group @Value(jira_group)",
              "color": "danger"
          }
          ]
      }
    UPLOAD_CONTENT_TYPE = Text (text/plain)
    UPLOAD_TYPE = Specify Upload Body
    USE_COOKIES = No
    VERIFY_SSL_CERTIFICATES = Yes
