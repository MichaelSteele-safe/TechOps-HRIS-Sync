FME workspace UkgImportOLD.fmw

Parameters:
- SLACK_NOTIFICATION_WEBHOOK = https://hooks.slack.com/services/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   # webhook to send notification to slack
- SHEETS_CONNECTION_GOOGLESHEETS = ellaine.chan Google Sheets   # "Google Sheets" Google Sheets Connection
- DestDataset_MYSQL_DB = set-rds-user   # (MySQL compatible) Connection
- DestDataset_MYSQL_DB_5 = set-rds-user   # (MySQL compatible) Connection
- DestDataset_MYSQL_DB_7 = set-rds-user   # (MySQL compatible) Connection
- DestDataset_MYSQL_DB_6 = set-rds-user   # (MySQL compatible) Connection
- GSHEETS_CONNECTION_SAFE.GOOGLE-SHEETS.GOOGLESHEETS4 = ellaine.chan Google Sheets (safe.google-sheets)   # "safe.google-sheets.Google Sheets" Google Sheets Connection

Writers:
- GOOGLESHEETS_1: GOOGLESHEETS
- CSV2_1: CSV2 to /Users/ellaine.chan/Desktop
- MYSQL_DB_1: MYSQL_DB to $(DestDataset_MYSQL_DB)
- MYSQL_DB_2: MYSQL_DB to $(DestDataset_MYSQL_DB_5)
- MYSQL_DB_3: MYSQL_DB to $(DestDataset_MYSQL_DB_7)
- MYSQL_DB_4: MYSQL_DB to $(DestDataset_MYSQL_DB_6)
- SAFE.GOOGLE-SHEETS.GOOGLESHEETS4_1: SAFE.GOOGLE-SHEETS.GOOGLESHEETS4
- AUTOMATIONS_1: AUTOMATIONS

Note: UKG Generated reports are sent to hrisautomation@safe.com, picked up by Google App Scripts and dropped to Google Drive. This workspace reads the latest CSV files to migrate data into our database. / Author: Ellaine Chan
Creator
    GEOMTYPE = Geometry Object
    NUM = 1
    CREATED -> GoogleDriveConnector
Note: List all files in the drive
GoogleDriveConnector
    GOOGLEDRIVE_NAMED_CONNECTION = ellaine.chan Google Drive
    OPERATION_TYPE = List
    PARAMETER_SETUP = _FME_FILES;1rjRm_CFXUfnNy3VOpvD_QQaHeIFgCVpN;_FME_INCLUDE_SUBFOLDERS;Yes;_FME_OBJECT_NAME_ATTRIBUTE;_name;_FME_OBJECT_ID_ATTRIBUTE;_id;_FME_OBJECT_PATH_ATTRIBUTE;_sharable_link;_FME_OBJECT_SIZE_ATTRIBUTE;_file_size;_FME_OBJECT_MODIFIED_ATTRIBUTE;_file_last_modified;_FME_OBJECT_TYPE_ATTRIBUTE;_file_or_folder;_FME_OBJECT_RELATIVE_PATH_ATTRIBUTE;_relative_path;FME_CONTROLLER_QUERY_FILE;transformers/dependencies/googledrive/List.fme;FME_CONTROLLER_CHOICE;List
    -> Sorter
Note: sort by date
Sorter
    SORT_PARM = _file_last_modified NATURAL DESCENDING
    SORTED -> Tester
Tester
    BOOL_OP = OR
    TEST_CLAUSE = CASE_INSENSITIVE_TEST @Value(_name) CONTAINS Employee
    TEST_MODE = CASE_INSENSITIVE_TEST
    PASSED -> Sampler
    FAILED -> Sampler_2
AttributeCreator_13
    ATTR_TABLE:
      SET_TO employee_payload = {
            "type": "employee",
            "first": "@Value(first)",
            "last": "@Value(last)",
            "email": "@Value(Employee Email)",
            "title": "@Value(title)"
        }
    -> HTTPCaller_20
    -> employee-payload-logger
employee-payload-logger: Logger
    LOG_FEATURE = LOG_ONLY
    MAXCOORDS = 20
    MAXFEATS = 20
    MESSAGE = @Value(employee_payload)
    SEVERITY = INFO
AttributeCreator_14
    ATTR_TABLE:
      SET_TO vendor_payload = {
            "type": "vendor",
            "first": "@Value(first)",
            "last": "@Value(last) (Vendor)",
            "email": "@Value(Employee Email)",
            "title": "@Value(title)"
        }
    -> HTTPCaller_22
    -> vendor-payload-logger
slack-notification-err: Logger
    LOG_FEATURE = LOG_ONLY
    MAXCOORDS = 20
    MAXFEATS = 20
    MESSAGE = @Value(_response_body)
    SEVERITY = ERROR
vendor-err-log: Logger
    LOG_FEATURE = LOG_ONLY
    MAXCOORDS = 20
    MAXFEATS = 20
    MESSAGE = @Value(_vendor_response_body)
    SEVERITY = INFO
vendor-payload-logger: Logger
    LOG_FEATURE = LOG_ONLY
    MAXCOORDS = 20
    MAXFEATS = 20
    MESSAGE = @Value(vendor_payload)
    SEVERITY = INFO

Bookmark: get slack ID and avatar if null
SQLCreator_2
    DATASET = set-rds-user
    EXPOSED_ATTRIBUTE_LIST = email,id
    FORMAT = MYSQL
    MYSQL_NAMED_CONNECTION = set-rds-user
    OUTPUT_FEATURES_DISPLAY = Schema and Data Features
    SQL_STATEMENT:
      select id, email from users.ukg_users
      where ( slack_id IS NULL or slack_id = "" or avatar_url = "" or avatar_url IS NULL)
      and deactivated is NULL
    RESULT -> HTTPCaller_17
HTTPCaller_17
    CONNECTION_TIMEOUT_LENGTH = 60
    CUSTOM_HEADERS = Authorization;Bearer xoxb-4573705574-1307285409845-phM9iicEYuXWd34uZcR4oVOH
    ERROR_ATTR = _error
    FOLLOW_REDIRECTS = FOLLOW_WITH_GET
    HTTP_METHOD = GET
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = https://slack.com/api/users.lookupByEmail?email=@Value(email)@safe.com
    TRANSFER_TIMEOUT_LENGTH = 90
    USE_COOKIES = No
    VERIFY_SSL_CERTIFICATES = Yes
    -> JSONExtractor_4
JSONExtractor_4
    EXTRACT_QUERY_TABLE = slack_id json["user"]["id"] avatar_url json["user"]["profile"]["image_192"]
    JSON_DOCUMENT = @Value(_response_body)
    READ_FROM_FILE = NO
    EVALUATED -> SQLExecutor_4 [INITIATOR]
SQLExecutor_4
    COMBINE_ATTRS = Result Attributes Only
    COMBINE_GEOM = Initiator Geometry Only
    DATASET = set-rds-user
    FORMAT = MYSQL
    MYSQL_NAMED_CONNECTION = set-rds-user
    OUTPUT_FEATURES_DISPLAY = Schema and Data Features
    SQL_STATEMENT:
      UPDATE users.ukg_users
      set slack_id = "@Value(slack_id)", avatar_url = "@Value(avatar_url)"
      where id = "@Value(id)"

Bookmark: employees
Note: Only process the latest 2 files
Sampler
    RATE = 2
    SAMPLE_MODE = No
    SAMPLE_TYPE_LONG = First N Features
    SAMPLED -> Counter
Counter
    CNT_ATTR = _count
    DOMAIN = counter
    SCOPE = Global
    START = 0
    -> GoogleDriveConnector_2
    -> Logger
Note: download latest two employee csv
GoogleDriveConnector_2
    GOOGLEDRIVE_NAMED_CONNECTION = ellaine.chan Google Drive
    OPERATION_TYPE = Download
    PARAMETER_SETUP = _FME_FILES;@Value(_id);_FME_DATA_TARGET;Attribute;_FME_TARGET_FOLDER;<Unused>;_FME_INCLUDE_SUBFOLDERS;<Unused>;_FME_TARGET_ATTRIBUTE;_contents;FME_CONTROLLER_QUERY_FILE;transformers/dependencies/googledrive/Download.fme;FME_CONTROLLER_CHOICE;Download
    -> Tester_8
Tester_8
    BOOL_OP = OR
    TEST_CLAUSE = TEST @Value(_count) = 0
    TEST_MODE = TEST
    PASSED -> TempPathnameCreator
    FAILED -> TempPathnameCreator_2
TempPathnameCreator
    EXTENSION = .csv
    PATHNAME_ATTR = _pathname
    -> AttributeFileWriter
Note: latest version
AttributeFileWriter
    CHAR_ENCODING = fme-system
    FILE_NAME = @Value(_pathname)
    OVERWRITE_FILE = Overwrite file
    SOURCE_ATTR = _contents
    -> FeatureReader_5 [INITIATOR]
FeatureReader_5
    ATTRS_TO_EXPOSE = Last Name First Name Preferred First Name Employee Number Employee Email Job Org Level 2 Code Org Level 2 Org Level 3 Code OL3 Alt Org Level 3 Work Extension Slack ID AD Login Office Number Office Floor Former Co-op OL2 Alt Org Level 1
    ATTR_ACCUM_MODE = Only Use Result
    COMBINE_GEOM = Use Result
    CSV2_CASE_SENSITIVE_FIELD_NAMES = Yes
    CSV2_CHUNK_SIZE = 100000
    CSV2_DATA_START_LINE = 2
    CSV2_DELIMITER = auto
    CSV2_ENCODING = UTF-8
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 10000
    CSV2_SCAN_TYPES = Yes
    CSV2_SKIP_DUPLICATE_DELIMITERS = No
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_USE_CUSTOM_SCHEMA = YES
    DATASET = @Value(_pathname)
    FORMAT = CSV2
    INTERACT = NONE
    OUTPUT_FEATURES_DISPLAY = Schema and Data Features
    <OTHER> -> AttributeCreator_2
Note: state is new
AttributeCreator_2
    ATTR_TABLE = SET_TO state = new
    -> Tester_2
TempPathnameCreator_2
    EXTENSION = .csv
    PATHNAME_ATTR = _pathname
    -> AttributeFileWriter_3
Note: Older version
AttributeFileWriter_3
    CHAR_ENCODING = fme-system
    FILE_NAME = @Value(_pathname)
    OVERWRITE_FILE = Overwrite file
    SOURCE_ATTR = _contents
    -> FeatureReader_3 [INITIATOR]
FeatureReader_3
    ATTRS_TO_EXPOSE = Last Name First Name Preferred First Name Employee Number Employee Email Job Org Level 2 Code Org Level 2 Org Level 3 Code Org Level 3 Work Extension AD Login Slack ID Office Number Office Floor Former Co-op OL3 Alt OL2 Alt Org Level 1
    ATTR_ACCUM_MODE = Only Use Result
    COMBINE_GEOM = Use Result
    CSV2_CASE_SENSITIVE_FIELD_NAMES = Yes
    CSV2_CHUNK_SIZE = 100000
    CSV2_DATA_START_LINE = 2
    CSV2_DELIMITER = auto
    CSV2_ENCODING = UTF-8
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 10000
    CSV2_SCAN_TYPES = Yes
    CSV2_SKIP_DUPLICATE_DELIMITERS = No
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_USE_CUSTOM_SCHEMA = YES
    DATASET = @Value(_pathname)
    FORMAT = CSV2
    INTERACT = NONE
    OUTPUT_FEATURES_DISPLAY = Schema and Data Features
    <OTHER> -> AttributeCreator
    <REJECTED> -> Terminator
Note: state is old
AttributeCreator
    ATTR_TABLE = SET_TO state = old
    -> Tester_2
Tester_2
    BOOL_OP = OR
    TEST_CLAUSE = TEST Employee Email ATTRIBUTE_HAS_A_VALUE ""
    TEST_MODE = TEST
    PASSED -> AttributeCreator_8
Note: create display name, default to preferred first name
AttributeCreator_8
    ATTR_TABLE = SET_TO display_name = @Value(Preferred First Name)
    -> NullAttributeMapper_9
Note: use first name as display name if null
NullAttributeMapper_9
    ATTRCHOICE = Selected Attributes
    ATTRLIST = display_name
    NEW_VALUE = @Value(First Name)
    NULL_TREATMENT = New Value
    SOURCE_ATTR_VAL = Null Empty "Missing (Selected Attributes Only)"
    -> NullAttributeMapper
    -> Tester_14
Note: use org 2 code as team_id if org 3 code is empty
NullAttributeMapper
    ATTRCHOICE = Selected Attributes
    ATTRLIST = Org Level 3 Code
    NEW_VALUE = @Value(Org Level 2 Code)
    NULL_TREATMENT = New Value
    SOURCE_ATTR_VAL = Null Empty "Missing (Selected Attributes Only)"
    -> NullAttributeMapper_6
Note: use org 2 as team if org 3 is empty
NullAttributeMapper_6
    ATTRCHOICE = Selected Attributes
    ATTRLIST = Org Level 3
    NEW_VALUE = @Value(Org Level 2)
    NULL_TREATMENT = New Value
    SOURCE_ATTR_VAL = Null Empty "Missing (Selected Attributes Only)"
    -> AttributeManager_7
Note: rename attributes to match db column names and remove "@safe.com" from email
AttributeManager_7
    ATTR_TABLE:
      RENAME_SET_VALUE Last Name > last
      RENAME_SET_VALUE First Name > first
      RENAME_SET_VALUE Preferred First Name > preferred_first_name
      RENAME_SET_VALUE Employee Number > id
      RENAME_SET_VALUE Job > title
      RENAME_SET_VALUE Org Level 3 Code > team_id
      RENAME_SET_VALUE Work Extension > work_extension
      RENAME_SET_VALUE AD Login > ldap
      REMOVE Slack ID
      RENAME_SET_VALUE Office Number > office_number
      RENAME_SET_VALUE Office Floor > office_floor
      RENAME_SET_VALUE Former Co-op > former_coop
    -> AttributeCreator_5
AttributeCreator_5
    ATTR_TABLE:
      SET_TO fme_where = id = @Value(id)
      SET_TO email = @ReplaceString(@Value(Employee Email),"@safe.com","")
    -> DateTimeStamper
DateTimeStamper
    DATETIME_ATTR = last_update
    INCLUDE_OFFSET = NO
    STAMP_TYPE = datetime
    TIMEZONE = utc
    -> Tester_9
Note: Is this the previous/older version?
Tester_9
    BOOL_OP = OR
    TEST_CLAUSE = TEST @Value(state) = old
    TEST_MODE = TEST
    PASSED -> ChangeDetector [ORIGINAL]
    FAILED -> ChangeDetector [REVISED]
    FAILED -> ukg_users (writer MYSQL_DB_3)
ChangeDetector
    BLANK_AND_MISSING_DIFFER = No
    BLANK_AND_MISSING_NAMES_TRAITS_DIFFER = No
    CHECK_COORDINATE_SYSTEMS = No
    CHECK_TYPES_AND_ENCODINGS = No
    LENIENT_MATCH = No
    MATCH = FULL
    MATCHATTRS = preferred_first_name title first last team_id office_floor office_number work_extension
    MATCH_STRATEGY = Match Selected Attributes
    PREEMPTIVE_ATTRS = id
    UNCHANGED_OUTPUT = Output Original
    UPDATED_LIST_NAME = _change_detection_list
    UPSERT_MODE = No
    UPDATED -> ListExploder
    INSERTED -> ukg_users (writer MYSQL_DB_4)
    INSERTED -> SQLExecutor_13 [INITIATOR]
    INSERTED -> HTTPCaller_4
    INSERTED -> AttributeCreator_13
    INSERTED -> AttributeCreator_14
    DELETED -> SQLExecutor_2 [INITIATOR]
    DELETED -> HTTPCaller_3
Note: Get one feature per change
ListExploder
    ATTR_ACCUM_MODE = Merge List Attributes
    ATTR_CONFLICT_RES = Use List Attribute Values
    INDEX_ATTR = _element_index
    LIST_ATTR = _change_detection_list{}
    ELEMENTS -> Tester_7
Tester_7
    BOOL_OP = OR
    TEST_CLAUSE = TEST @Value(attributeName) = team_id
    TEST_MODE = TEST
    PASSED -> SQLExecutor_6 [INITIATOR]
    FAILED -> NullAttributeMapper_8
ukg_users (writer MYSQL_DB_4)
    attributes: last varchar(200), first varchar(200), preferred_first_name varchar(200), id varchar(200), email varchar(200), title varchar(200), team_id varchar(200), work_extension varchar(200), ldap varchar(200), office_number varchar(200), office_floor varchar(200), former_coop varchar(200), last_update text
ukg_users (writer MYSQL_DB_3)
    attributes: last varchar(200), first varchar(200), preferred_first_name varchar(200), id varchar(200), email varchar(200), title varchar(200), team_id varchar(200), work_extension varchar(200), ldap varchar(200), office_number varchar(200), office_floor varchar(200), former_coop varchar(200), last_update text
Terminator
    MESSAGE = Translation Terminated
Logger
    LOG_FEATURE = LOG_ONLY
    MAXCOORDS = 20
    MAXFEATS = 20
    MESSAGE = Downloading... @Value(_name)
    SEVERITY = INFO

Bookmark: Update Jira Group
Tester_14
    BOOL_OP = OR
    TEST_CLAUSE = CASE_INSENSITIVE_TEST @Value(state) = old
    TEST_MODE = CASE_INSENSITIVE_TEST
    FAILED -> Tester_16
Note: Only try to get alt_name if org3 exists
Tester_16
    BOOL_OP = OR
    TEST_CLAUSE = TEST Org Level 3 Code ATTRIBUTE_HAS_A_VALUE ""
    TEST_MODE = TEST
    PASSED -> SQLExecutor_8 [INITIATOR]
    FAILED -> AttributeCreator_9
Note: get alt_name
SQLExecutor_8
    ATTR_IGNORE_NULLS = Yes
    COMBINE_ATTRS = Keep Result Attributes if Conflict
    COMBINE_GEOM = Initiator Geometry Only
    DATASET = set-rds-user
    EXPOSED_ATTRIBUTE_LIST = alt_name
    FORMAT = MYSQL
    MYSQL_NAMED_CONNECTION = set-rds-user
    OUTPUT_FEATURES_DISPLAY = Schema and Data Features
    SQL_STATEMENT = select alt_name from users.ukg_teams where id = "@Value(Org Level 3 Code)"
    RESULT -> HTTPCaller_8
AttributeCreator_9
    ATTR_TABLE = SET_TO alt_name
    -> HTTPCaller_8
Note: get accountId
HTTPCaller_8
    CONNECTION_TIMEOUT_LENGTH = 60
    CUSTOM_HEADERS = Authorization;Basic amlyYWFwaUBzYWZlLmNvbTpZN3lwbkZha2g1V1BPVUhSbkJPUTVEQjE=
    ERROR_ATTR = _error
    FOLLOW_REDIRECTS = FOLLOW_WITH_GET
    HTTP_METHOD = GET
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _user_response_body
    TARGET_ATTR_ENCODING = auto-detect
    TARGET_URL = https://safesoftware.atlassian.net/rest/api/3/user/search?query=@Value(Employee Email)
    TRANSFER_TIMEOUT_LENGTH = 90
    USE_COOKIES = No
    VERIFY_SSL_CERTIFICATES = Yes
    -> JSONExtractor
Note: extract accountId and jira_avatar
JSONExtractor
    EXTRACT_QUERY_TABLE = accountId json[*]["accountId"] jira_avatar json[*]["avatarUrls"]["48x48"]
    JSON_DOCUMENT = @Value(_user_response_body)
    READ_FROM_FILE = NO
    EVALUATED -> Tester_17
    EVALUATED -> SQLExecutor [INITIATOR]
Tester_17
    BOOL_OP = OR
    TEST_CLAUSE = TEST accountId ATTRIBUTE_HAS_A_VALUE ""
    TEST_MODE = TEST
    PASSED -> HTTPCaller_9
Note: get groups that user is in
HTTPCaller_9
    CONNECTION_TIMEOUT_LENGTH = 60
    CUSTOM_HEADERS = Authorization;Basic amlyYWFwaUBzYWZlLmNvbTpZN3lwbkZha2g1V1BPVUhSbkJPUTVEQjE=
    ERROR_ATTR = _error
    FOLLOW_REDIRECTS = FOLLOW_WITH_GET
    HTTP_METHOD = GET
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _user_group_response_body
    TARGET_ATTR_ENCODING = auto-detect
    TARGET_URL = https://safesoftware.atlassian.net/rest/api/3/user?accountId=@Value(accountId)&expand=groups
    TRANSFER_TIMEOUT_LENGTH = 90
    USE_COOKIES = No
    VERIFY_SSL_CERTIFICATES = Yes
    -> AttributeCreator_4
AttributeCreator_4
    ATTR_TABLE:
      SET_TO group_operation
      SET_TO jira_group
    -> PythonCaller
    -> PythonCaller_5
Note: Maintain group-customer-support
PythonCaller_5
    PYTHONSOURCE:
      import fme
      import fmeobjects
      import json


      class FeatureProcessor(object):
          """Template Class Interface:
          When using this class, make sure its name is set as the value of the 'Class
          to Process Features' transformer parameter.
          """

          def __init__(self):
              """Base constructor for class members."""
              pass

          def input(self, feature):
              user_group_name_list = []
              customer_success_group = "group-customer-support"
              user_groups_list = json.loads(feature.getAttribute('_user_group_response_body'))["groups"]["items"]
              in_customer_success_group = False
              if feature.getAttribute('Org Level 2 Code') == "CS3000" and feature.getAttribute('Org Level 3 Code') != "CS3120" and feature.getAttribute('Org Level 3 Code') != "CS3140":
                  in_customer_success_group = True
              for group in user_groups_list:
                  user_group_name_list.append(group["name"])
                  if in_customer_success_group == False and group["name"] == customer_success_group:
                      new_feature = feature.clone()
                      new_feature.setAttribute('group_operation', 'delete')
                      new_feature.setAttribute('jira_group', customer_success_group)
                      self.pyoutput(new_feature)
              if in_customer_success_group and customer_success_group not in user_group_name_list:
                  new_feature = feature.clone()
                  new_feature.setAttribute('group_operation', 'add')
                  new_feature.setAttribute('jira_group', customer_success_group)
                  self.pyoutput(new_feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> HTTPCaller_13
Note: Determine which groups user needs to be added or removed from and output as new feature
PythonCaller
    PYTHONSOURCE:
      import fme
      import fmeobjects
      import json


      class FeatureProcessor(object):
          """Template Class Interface:
          When using this class, make sure its name is set as the value of the 'Class
          to Process Features' transformer parameter.
          """

          def __init__(self):
              """Base constructor for class members."""
              pass


          def input(self, feature):
              user_groups_list = json.loads(feature.getAttribute('_user_group_response_body'))["groups"]["items"]
              user_group_name_list = []
              org3_jira_name = ""
              org2_jira_name = ""
              org1_jira_name = org1_jira_name =  "team-" + feature.getAttribute('Org Level 1').replace("- ", "" ).replace(" ", "-" ).lower()
              if feature.getAttribute('OL3 Alt') == None or len(feature.getAttribute('OL3 Alt')) == 0:
                  org3_jira_name =  "team-" + feature.getAttribute('Org Level 3').replace("- ", "" ).replace(" ", "-" ).lower()
              else:
                  org3_jira_name =  "team-" + feature.getAttribute('OL3 Alt').replace("- ", "" ).replace(" ", "-" ).lower()
              if feature.getAttribute('OL2 Alt') == None or len(feature.getAttribute('OL2 Alt')) == 0:
                  org2_jira_name =  "team-" + feature.getAttribute('Org Level 2').replace("- ", "" ).replace(" ", "-" ).lower()
              else:
                  org2_jira_name =  "team-" + feature.getAttribute('OL2 Alt').replace("- ", "" ).replace(" ", "-" ).lower()
              print(feature.getAttribute('display_name'))
              print(org3_jira_name)
              print(org2_jira_name)
              print(org1_jira_name)
              for group in user_groups_list:
                  print("group: %s" % group["name"])
                  user_group_name_list.append(group["name"])
                  # don't remove PMs from their dev team
                  org3_name =  feature.getAttribute('Org Level 3').replace("Product Mgmt", "Product Management")
                  if group["name"] != org1_jira_name and group["name"] != org2_jira_name and group["name"] != org3_jira_name and group["name"].find("team") ==0:
                      if "Product Management" in org3_name:
                          dev_team = org3_name.replace("Product Management", "").rstrip().lower()
                          if dev_team not in group["name"]:
                              new_feature = feature.clone()
                              new_feature.setAttribute('group_operation', 'delete')
                              new_feature.setAttribute('jira_group', group["name"])
                              self.pyoutput(new_feature)
                      else:
                          new_feature = feature.clone()
                          new_feature.setAttribute('group_operation', 'delete')
                          new_feature.setAttribute('jira_group', group["name"])
                          self.pyoutput(new_feature)
              if not org1_jira_name in user_group_name_list:
                  new_feature = feature.clone()
                  new_feature.setAttribute('group_operation', 'add')
                  new_feature.setAttribute('jira_group', org1_jira_name)
                  self.pyoutput(new_feature)
              if not org2_jira_name in user_group_name_list:
                  new_feature = feature.clone()
                  new_feature.setAttribute('group_operation', 'add')
                  new_feature.setAttribute('jira_group', org2_jira_name)
                  self.pyoutput(new_feature)
              if not org3_jira_name in user_group_name_list:
                  if feature.getAttribute('Org Level 3 Code') != None and len(feature.getAttribute('Org Level 3')) > 1:
                      new_feature = feature.clone()
                      new_feature.setAttribute('group_operation', 'add')
                      new_feature.setAttribute('jira_group', org3_jira_name)
                      self.pyoutput(new_feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass
    PYTHONSYMBOL = FeatureProcessor
    -> HTTPCaller_13
Note: get groupId
HTTPCaller_13
    CONNECTION_TIMEOUT_LENGTH = 60
    CUSTOM_HEADERS = Authorization;Basic amlyYWFwaUBzYWZlLmNvbTpZN3lwbkZha2g1V1BPVUhSbkJPUTVEQjE=
    ERROR_ATTR = _error
    FOLLOW_REDIRECTS = FOLLOW_WITH_GET
    HTTP_METHOD = GET
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _jira_group_response_body
    TARGET_ATTR_ENCODING = auto-detect
    TARGET_URL = https://safesoftware.atlassian.net/rest/api/3/groups/picker?query=@Value(jira_group)
    TRANSFER_TIMEOUT_LENGTH = 90
    USE_COOKIES = No
    VERIFY_SSL_CERTIFICATES = Yes
    -> JSONExtractor_2
Note: extract groupId
JSONExtractor_2
    EXTRACT_QUERY_TABLE = groupId json["groups"][0]["groupId"] groupName json["groups"][0]["name"]
    JSON_DOCUMENT = @Value(_jira_group_response_body)
    READ_FROM_FILE = NO
    EVALUATED -> Tester_10
Tester_10
    BOOL_OP = OR
    TEST_CLAUSE = TEST @Value(group_operation) = add
    TEST_MODE = TEST
    PASSED -> Tester_15
    FAILED -> Tester_13
Note: does group already exist?
Tester_15
    BOOL_OP = AND
    TEST_CLAUSE:
      TEST groupId ATTRIBUTE_HAS_A_VALUE ""
      TEST @Value(groupName) = @Value(jira_group)
    TEST_MODE = TEST
    PASSED -> AttributeCreator_11
    FAILED -> DuplicateFilter_2
DuplicateFilter_2
    INPUT_ORDERED_CHOICE = No
    KEYATTR = jira_group
    UNIQUE -> HTTPCaller_14
    DUPLICATE -> FeatureJoiner [RIGHT]
Note: create jira group
HTTPCaller_14
    CONNECTION_TIMEOUT_LENGTH = 60
    CUSTOM_HEADERS = Authorization;Basic ZWxsYWluZS5jaGFuQHNhZmUuY29tOkFYZHF4VDRaSmZjdHV1dVRXUnF1QTRENw==
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _new_group_response_body
    TARGET_ATTR_ENCODING = auto-detect
    TARGET_URL = https://safesoftware.atlassian.net/rest/api/3/group
    TRANSFER_TIMEOUT_LENGTH = 90
    UPLOAD_BODY:
      {
          "name": "@Value(jira_group)"
      }
    UPLOAD_CONTENT_TYPE = JSON (application/json)
    UPLOAD_TYPE = Specify Upload Body
    USE_COOKIES = No
    VERIFY_SSL_CERTIFICATES = Yes
    -> JSONExtractor_3
Note: extract groupId
JSONExtractor_3
    EXTRACT_QUERY_TABLE = groupId json["groupId"]
    JSON_DOCUMENT = @Value(_new_group_response_body)
    READ_FROM_FILE = NO
    EVALUATED -> HTTPCaller_11
    EVALUATED -> AttributeCreator_11
    EVALUATED -> AttributeKeeper
Note: notify techops_automation jira group was created
HTTPCaller_11
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - Created Jira Group",
              "text": "@Value(jira_group)",
              "color": "good"
          }
          ]
      }
    UPLOAD_CONTENT_TYPE = Text (text/plain)
    UPLOAD_TYPE = Specify Upload Body
    USE_COOKIES = No
    VERIFY_SSL_CERTIFICATES = Yes
AttributeKeeper
    CREATE_BULK_MODE_FEATURES = NO
    KEEP_ATTRS = groupId,jira_group
    -> FeatureJoiner [LEFT]
FeatureJoiner
    ATTR_CONFLICT_RES = Prefer Left
    GEOMETRY_HANDLING = Prefer Left
    JOIN_KEYS = jira_group jira_group AUTO
    JOIN_MODE = Left
    JOINED -> AttributeCreator_11
AttributeCreator_11
    ATTR_TABLE:
      SET_TO add_url = https://safesoftware.atlassian.net/rest/api/3/group/user?groupId=@Value(groupId)
      SET_TO url_body = {
            "accountId": "@Value(accountId)"
        }
    -> HTTPCaller_16
Note: add user to jira group
HTTPCaller_16
    CONNECTION_TIMEOUT_LENGTH = 60
    CUSTOM_HEADERS = Authorization;Basic ZWxsYWluZS5jaGFuQHNhZmUuY29tOkFYZHF4VDRaSmZjdHV1dVRXUnF1QTRENw==
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _new_group_response_body
    TARGET_ATTR_ENCODING = auto-detect
    TARGET_URL = https://safesoftware.atlassian.net/rest/api/3/group/user?groupId=@Value(groupId)
    TRANSFER_TIMEOUT_LENGTH = 90
    UPLOAD_BODY:
      {
          "accountId": "@Value(accountId)"
      }
    UPLOAD_CONTENT_TYPE = JSON (application/json)
    UPLOAD_TYPE = Specify Upload Body
    USE_COOKIES = No
    VERIFY_SSL_CERTIFICATES = Yes
    -> HTTPCaller_12
Note: notify techops_automation user was added to group
HTTPCaller_12
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - User added to Jira Group",
              "text": "Employee @Value(display_name) @Value(Last Name) was added to @Value(jira_group)",
              "color": "good"
          }
          ]
      }
    UPLOAD_CONTENT_TYPE = Text (text/plain)
    UPLOAD_TYPE = Specify Upload Body
    USE_COOKIES = No
    VERIFY_SSL_CERTIFICATES = Yes
Note: EXCEPTIONS
Tester_13
    BOOL_OP = OR
    TEST_CLAUSE:
      TEST @Value(jira_group) = team-facilities
      CASE_INSENSITIVE_TEST john.leesbonnie.alexander CONTAINS @Value(Employee Email)
    TEST_MODE = PER_TEST
    FAILED -> AttributeCreator_10
AttributeCreator_10
    ATTR_TABLE = SET_TO delete_url = https://safesoftware.atlassian.net/rest/api/3/group/user?groupId=@Value(groupId)&accountId=@Value(accountId)
    -> HTTPCaller_18
Note: remove user from group
HTTPCaller_18
    CONNECTION_TIMEOUT_LENGTH = 60
    CUSTOM_HEADERS = Authorization;Basic ZWxsYWluZS5jaGFuQHNhZmUuY29tOkFYZHF4VDRaSmZjdHV1dVRXUnF1QTRENw==
    ERROR_ATTR = _error
    FOLLOW_REDIRECTS = FOLLOW_WITH_GET
    HTTP_METHOD = DELETE
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _remove_user_from_group_response_body
    TARGET_ATTR_ENCODING = auto-detect
    TARGET_URL = https://safesoftware.atlassian.net/rest/api/3/group/user?groupId=@Value(groupId)&accountId=@Value(accountId)
    TRANSFER_TIMEOUT_LENGTH = 90
    UPLOAD_BODY:
      {
          "accountId": "@Value(accountId)"
      }
    UPLOAD_CONTENT_TYPE = JSON (application/json)
    UPLOAD_TYPE = Specify Upload Body
    USE_COOKIES = No
    VERIFY_SSL_CERTIFICATES = Yes
    -> HTTPCaller_10
Note: notify techops_automation of removed from jira group
HTTPCaller_10
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - User removed from Jira Group",
              "text": "Employee @Value(display_name) @Value(Last Name) was removed from group @Value(jira_group)",
              "color": "danger"
          }
          ]
      }
    UPLOAD_CONTENT_TYPE = Text (text/plain)
    UPLOAD_TYPE = Specify Upload Body
    USE_COOKIES = No
    VERIFY_SSL_CERTIFICATES = Yes

Bookmark: Update Employee DB Tasks
Note: Update jira avatar
SQLExecutor
    COMBINE_ATTRS = Result Attributes Only
    COMBINE_GEOM = Initiator Geometry Only
    DATASET = set-rds-user
    FORMAT = MYSQL
    MYSQL_NAMED_CONNECTION = set-rds-user
    OUTPUT_FEATURES_DISPLAY = Schema and Data Features
    SQL_STATEMENT:
      UPDATE users.ukg_users
      set jira_avatar = "@Value(jira_avatar)"
      WHERE id = @Value(Employee Number)
SQLExecutor_6
    ATTR_IGNORE_NULLS = Yes
    COMBINE_ATTRS = Keep Initiator Attributes if Conflict
    COMBINE_GEOM = Initiator Geometry Only
    DATASET = set-rds-user
    EXPOSED_ATTRIBUTE_LIST = original_team_name
    FORMAT = MYSQL
    MYSQL_HANDLE_UTC_OFFSET = Yes
    MYSQL_NAMED_CONNECTION = set-rds-user
    MYSQL_QUERY_FEATURE_TYPES_FOR_MERGE_FILTERS = Yes
    OUTPUT_FEATURES_DISPLAY = Schema and Data Features
    SQL_STATEMENT = select name as original_team_name from users.ukg_teams where id = "@Value(originalValue)"
    RESULT -> SQLExecutor_7 [INITIATOR]
SQLExecutor_7
    ATTR_IGNORE_NULLS = Yes
    COMBINE_ATTRS = Keep Initiator Attributes if Conflict
    COMBINE_GEOM = Initiator Geometry Only
    DATASET = set-rds-user
    EXPOSED_ATTRIBUTE_LIST = revised_team_name,revised_alt_name
    FORMAT = MYSQL
    MYSQL_HANDLE_UTC_OFFSET = Yes
    MYSQL_NAMED_CONNECTION = set-rds-user
    MYSQL_QUERY_FEATURE_TYPES_FOR_MERGE_FILTERS = Yes
    OUTPUT_FEATURES_DISPLAY = Schema and Data Features
    SQL_STATEMENT = select name as revised_team_name, alt_name as revised_alt_name from users.ukg_teams where id = "@Value(revisedValue)"
    RESULT -> HTTPCaller_7
Note: notify techops_automation of employee team updates
HTTPCaller_7
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - Employee updated",
              "text": "Employee @Value(id) (@Value(display_name) @Value(last)) \n Field: @Value(attributeName)\n  ~@Value(originalValue)/@Value(original_team_name)~ -> @Value(revisedValue)/@Value(revised_team_name)",
              "color": "warning"
          }
          ]
      }
    UPLOAD_CONTENT_TYPE = Text (text/plain)
    UPLOAD_TYPE = Specify Upload Body
    USE_COOKIES = No
    VERIFY_SSL_CERTIFICATES = Yes
NullAttributeMapper_8
    ATTRCHOICE = Selected Attributes
    ATTRLIST = originalValue revisedValue
    NEW_VALUE = Null
    NULL_TREATMENT = New Value
    SOURCE_ATTR_VAL = Null Empty "Missing (Selected Attributes Only)"
    -> HTTPCaller
Note: notify techops_automation of updates
HTTPCaller
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - Employee updated",
              "text": "Employee @Value(id) (@Value(display_name) @Value(last)) \n Field: @Value(attributeName)\n  ~@Value(originalValue)~ -> @Value(revisedValue)",
              "color": "warning"
          }
          ]
      }
    UPLOAD_CONTENT_TYPE = Text (text/plain)
    UPLOAD_TYPE = Specify Upload Body
    USE_COOKIES = No
    VERIFY_SSL_CERTIFICATES = Yes

Bookmark: New Employee non-db Tasks
Note: create employee in netsuite
HTTPCaller_20
    CONNECTION_TIMEOUT_LENGTH = 60
    CUSTOM_HEADERS = x-api-key;HE1VkuRek09M1i9h1bMRN1E5VrLYgcGc6cpetg8V
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _employee_response_body
    TARGET_ATTR_ENCODING = auto-detect
    TARGET_URL = https://oywucjcctjfxq3rchcesb6653e0lgqpr.lambda-url.us-west-2.on.aws
    TRANSFER_TIMEOUT_LENGTH = 90
    UPLOAD_BODY:
      {
          "type": "employee",
          "first": "@Value(first)",
          "last": "@Value(last)",
          "email": "@Value(Employee Email)",
          "title": "@Value(title)"
      }
    UPLOAD_CONTENT_TYPE = JSON (application/json)
    UPLOAD_TYPE = Specify Upload Body
    USE_COOKIES = No
    VERIFY_SSL_CERTIFICATES = Yes
    -> HTTPCaller_19
    <REJECTED> -> employee-err-log
    <REJECTED> -> HTTPCaller_21
Note: notify techops_automation of netsuite creation
HTTPCaller_19
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - Netsuite addition",
              "text": "Employee @Value(id) @Value(display_name) @Value(last) has been added to Netsuite",
              "color": "good"
          }
          ]
      }
    UPLOAD_CONTENT_TYPE = JSON (application/json)
    UPLOAD_TYPE = Specify Upload Body
    USE_COOKIES = No
    VERIFY_SSL_CERTIFICATES = Yes
Note: notify techops_automation of netsuite creation
HTTPCaller_21
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "Could not add employee @Value(id) (@Value(display_name) @Value(last)) to Netsuite",
              "text": "@Value(_employee_response_body)",
              "color": "danger"
          }
          ]
      }
    UPLOAD_CONTENT_TYPE = JSON (application/json)
    UPLOAD_TYPE = Specify Upload Body
    USE_COOKIES = No
    VERIFY_SSL_CERTIFICATES = Yes
    <REJECTED> -> slack-notification-err
employee-err-log: Logger
    LOG_FEATURE = LOG_ONLY
    MAXCOORDS = 20
    MAXFEATS = 20
    MESSAGE = @Value(_employee_response_body)
    SEVERITY = ERROR
Note: create vendor in netsuite
HTTPCaller_22
    CONNECTION_TIMEOUT_LENGTH = 60
    CUSTOM_HEADERS = x-api-key;HE1VkuRek09M1i9h1bMRN1E5VrLYgcGc6cpetg8V
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _vendor_response_body
    TARGET_ATTR_ENCODING = auto-detect
    TARGET_URL = https://oywucjcctjfxq3rchcesb6653e0lgqpr.lambda-url.us-west-2.on.aws
    TRANSFER_TIMEOUT_LENGTH = 90
    UPLOAD_BODY:
      {
          "type": "vendor",
          "first": "@Value(first)",
          "last": "@Value(last) (Vendor)",
          "email": "@Value(Employee Email)",
          "title": "@Value(title)"
      }
    UPLOAD_CONTENT_TYPE = JSON (application/json)
    UPLOAD_TYPE = Specify Upload Body
    USE_COOKIES = No
    VERIFY_SSL_CERTIFICATES = Yes
    -> HTTPCaller_23
    <REJECTED> -> HTTPCaller_24
    <REJECTED> -> vendor-err-log
Note: notify techops_automation of netsuite creation
HTTPCaller_23
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - Netsuite addition",
              "text": "Vendor @Value(id) @Value(display_name) @Value(last) (Vendor) has been added to Netsuite",
              "color": "good"
          }
          ]
      }
    UPLOAD_CONTENT_TYPE = Text (text/plain)
    UPLOAD_TYPE = Specify Upload Body
    USE_COOKIES = No
    VERIFY_SSL_CERTIFICATES = Yes
Note: notify techops_automation of netsuite creation
HTTPCaller_24
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "Could not add vendor to Netsuite",
              "text": "Failed to add vendor @Value(id) (@Value(display_name) @Value(last) (Vendor)) to Netsuite",
              "color": "danger"
          }
          ]
      }
    UPLOAD_CONTENT_TYPE = Text (text/plain)
    UPLOAD_TYPE = Specify Upload Body
    USE_COOKIES = No
    VERIFY_SSL_CERTIFICATES = Yes
    <REJECTED> -> slack-notification-err

Bookmark: New Employee DB tasks
Note: notify techops_automation of employee activation
HTTPCaller_4
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - Employee Added",
              "text": "Employee @Value(id) (@Value(display_name) @Value(last))",
              "color": "good"
          }
          ]
      }
    UPLOAD_CONTENT_TYPE = Text (text/plain)
    UPLOAD_TYPE = Specify Upload Body
    USE_COOKIES = No
    VERIFY_SSL_CERTIFICATES = Yes
Note: check if new user is in a development team
SQLExecutor_13
    ATTR_IGNORE_NULLS = Yes
    COMBINE_ATTRS = Keep Initiator Attributes if Conflict
    COMBINE_GEOM = Initiator Geometry Only
    DATASET = set-rds-user
    EXPOSED_ATTRIBUTE_LIST = development
    FORMAT = MYSQL
    MYSQL_HANDLE_UTC_OFFSET = Yes
    MYSQL_NAMED_CONNECTION = set-rds-user
    MYSQL_QUERY_FEATURE_TYPES_FOR_MERGE_FILTERS = Yes
    OUTPUT_FEATURES_DISPLAY = Schema and Data Features
    SQL_STATEMENT:
      select development from users.ukg_teams
      where id = "@Value(team_id)"
    RESULT -> Tester_6
    RESULT -> AttributeCreator_6
Note: is user a dev?
Tester_6
    BOOL_OP = OR
    TEST_CLAUSE = TEST @Value(development) = 1
    TEST_MODE = TEST
    PASSED -> AttributeCreator_7
    PASSED -> AttributeCreator_15
Note: create svn
AttributeCreator_7
    ATTR_TABLE:
      SET_TO _svn_initials
      SET_TO _temp_svn = @LowerCase(@Left(@Value(display_name),1)@Left(@Value(last),1))
    -> PythonCaller_4
Note: create gtb-1_username
AttributeCreator_15
    ATTR_TABLE = SET_TO gtb-1 = @LowerCase(@ReplaceString(@Value(first)," ","-",caseSensitive=TRUE))-@LowerCase(@Value(last))
    -> SQLExecutor_9 [INITIATOR]
Note: save gtb-1 username
SQLExecutor_9
    ATTR_IGNORE_NULLS = Yes
    COMBINE_ATTRS = Keep Initiator Attributes if Conflict
    COMBINE_GEOM = Initiator Geometry Only
    DATASET = set-rds-user
    EXPOSED_ATTRIBUTE_LIST = revised_team_name,revised_alt_name
    FORMAT = MYSQL
    MYSQL_HANDLE_UTC_OFFSET = Yes
    MYSQL_NAMED_CONNECTION = set-rds-user
    MYSQL_QUERY_FEATURE_TYPES_FOR_MERGE_FILTERS = Yes
    OUTPUT_FEATURES_DISPLAY = Schema and Data Features
    SQL_STATEMENT:
      update users.ukg_users
      set `gtb-1_username` = "@Value(gtb-1)"
      where id = @Value(id) limit 1
Note: Create temp_ldap
AttributeCreator_6
    ATTR_TABLE:
      SET_TO _ldap
      SET_TO _temp_ldap = @LowerCase(@Left(@Value(display_name),1)@Value(last))
    -> PythonCaller_3
SQLCreator
    DATASET = set-rds-user
    EXPOSED_ATTRIBUTE_LIST = _ldap,_svn_initials
    FORMAT = MYSQL
    MYSQL_HANDLE_UTC_OFFSET = Yes
    MYSQL_NAMED_CONNECTION = set-rds-user
    MYSQL_QUERY_FEATURE_TYPES_FOR_MERGE_FILTERS = Yes
    OUTPUT_FEATURES_DISPLAY = Schema and Data Features
    SQL_STATEMENT = SELECT ldap as _ldap, code_signature as _svn_initials from users.ukg_users
    RESULT -> PythonCaller_3
    RESULT -> PythonCaller_4
Note: Create unique svn_initials for active users on a development team
PythonCaller_4
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              self.featureList = []
              self._svn_list = []
          def input(self,feature):
              self.featureList.append(feature)
              if feature.getAttribute('_svn_initials'):
                  self._svn_list.append(feature.getAttribute('_svn_initials'))
          def close(self):
              from string import ascii_lowercase
              for feature in self.featureList:
                  if feature.getAttribute('_temp_svn'):
                      if feature.getAttribute('_temp_svn') in self._svn_list:
                          alphabet = ascii_lowercase[::-1]
                          svn_unique = False
                          count = 0
                          while svn_unique == False and count < 26:
                              initial =  feature.getAttribute('display_name')[0].lower() + alphabet[count] + feature.getAttribute('last')[0].lower()
                              count = count + 1
                              if initial not in self._svn_list:
                                  feature.setAttribute('_svn_initials', initial.lower())
                                  self._svn_list.append(initial)
                                  svn_unique = True
                          if svn_unique == False:
                                feature.setAttribute('_svn_initials', 'Error')
                      else:
                          initial = feature.getAttribute('_temp_svn')
                          feature.setAttribute('_svn_initials', initial)
                      self.pyoutput(feature)
    PYTHONSYMBOL = FeatureProcessor
    -> Tester_19
Tester_19
    BOOL_OP = OR
    TEST_CLAUSE = TEST @Value(_svn_initials) = Error
    TEST_MODE = TEST
    PASSED -> HTTPCaller_15
    FAILED -> SQLExecutor_11 [INITIATOR]
Note: notify techops_automation something went wrong with svn_initials generation
HTTPCaller_15
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - SVN initials error",
              "text": "Could not create svn initials for employee @Value(id) (@Value(preferred_first_name) @Value(last)) <@ellaine.chan>",
              "color": "danger"
          }
          ]
      }
    UPLOAD_CONTENT_TYPE = Text (text/plain)
    UPLOAD_TYPE = Specify Upload Body
    USE_COOKIES = No
    VERIFY_SSL_CERTIFICATES = Yes
SQLExecutor_11
    ATTR_IGNORE_NULLS = Yes
    COMBINE_ATTRS = Keep Initiator Attributes if Conflict
    COMBINE_GEOM = Initiator Geometry Only
    DATASET = set-rds-user
    EXPOSED_ATTRIBUTE_LIST = revised_team_name,revised_alt_name
    FORMAT = MYSQL
    MYSQL_HANDLE_UTC_OFFSET = Yes
    MYSQL_NAMED_CONNECTION = set-rds-user
    MYSQL_QUERY_FEATURE_TYPES_FOR_MERGE_FILTERS = Yes
    OUTPUT_FEATURES_DISPLAY = Schema and Data Features
    SQL_STATEMENT:
      update users.ukg_users
      set code_signature = "@Value(_svn_initials)"
      where email = "@Value(email)" limit 1
Note: Create unique ldap and notify on slack
PythonCaller_3
    NEW_ATTRIBUTES = first last _new_ldap
    PYTHONSOURCE:
      import fme
      import fmeobjects
      import requests
      import json

      def send_slack_message(message):
          url = "%s" % FME_MacroValues['SLACK_NOTIFICATION_WEBHOOK']
          print("URL: " + url)
          body = {
              "attachments": [{
                  "title": "HRIS - LDAP created",
                  "text": message,
                  "color": "good"
              }]
          }
          print(message)
          response = requests.post(url, data=json.dumps(body))
          print("RESPONSE \n %s" % response)
          return response

      class FeatureProcessor(object):
          def __init__(self):
              self.featureList = []
              self.ldapList = []
              self.ldapNoConflictList = []
              self.errorList = []
          def input(self,feature):
              self.featureList.append(feature)
              if feature.getAttribute('_ldap'):
                  self.ldapList.append(feature.getAttribute('_ldap'))

          def close(self):
              from string import ascii_lowercase

              for feature in self.featureList:
                  if feature.getAttribute('_temp_ldap'):
                      if feature.getAttribute('_temp_ldap') in self.ldapList:
                          self.errorList.append(feature.getAttribute('email')) #this new user has the same name as existing user
                          alphabet = ascii_lowercase[::-1]
                          ldap_unique = False
                          while ldap_unique == False :
                              for letter in alphabet:
                                  templdap = feature.getAttribute('display_name')[0] + letter + feature.getAttribute('last')
                                  templdap = templdap.lower()
                                  if templdap not in self.ldapList:
                                      print("NOT IN CONFLICT ADD TO LIST %s" % feature.getAttribute('email'))
                                      self.ldapNoConflictList.append(feature.getAttribute('email'))
                                      feature.setAttribute('_ldap', templdap)
                                      self.ldapList.append(templdap)
                                      ldap_unique = True
                                      break
                              if ldap_unique == False:
                                  feature.setAttribute('_ldap', 'Error')
                                  break
                      else:
                          self.ldapNoConflictList.append(feature.getAttribute('email'))
                          templdap = feature.getAttribute('_temp_ldap')
                          feature.setAttribute('_ldap', templdap)
                          self.ldapList.append(templdap)
                      if feature.getAttribute('email') in self.ldapNoConflictList:
                          user = feature.getAttribute('email')
                          ldap = feature.getAttribute('_ldap')
                          createMessage = ("*New User*\n User `{}` has been given network ID `{}` (no conflicts identified)".format(user, ldap))
                          send_slack_message(createMessage)
                      if feature.getAttribute('email') in self.errorList:
                          user = feature.getAttribute('email')
                          ldap = feature.getAttribute('_ldap')
                          createMessage = ("*New User*\n User `{}` has been given network ID `{}` (conflicts identified) <@ellaine.chan>\n".format(user, ldap, user))
                          send_slack_message(createMessage)
                      self.pyoutput(feature)
    PYTHONSYMBOL = FeatureProcessor
    -> SQLExecutor_12 [INITIATOR]
SQLExecutor_12
    ATTR_IGNORE_NULLS = Yes
    COMBINE_ATTRS = Keep Initiator Attributes if Conflict
    COMBINE_GEOM = Initiator Geometry Only
    DATASET = set-rds-user
    EXPOSED_ATTRIBUTE_LIST = revised_team_name,revised_alt_name
    FORMAT = MYSQL
    MYSQL_HANDLE_UTC_OFFSET = Yes
    MYSQL_NAMED_CONNECTION = set-rds-user
    MYSQL_QUERY_FEATURE_TYPES_FOR_MERGE_FILTERS = Yes
    OUTPUT_FEATURES_DISPLAY = Schema and Data Features
    SQL_STATEMENT:
      update users.ukg_users
      set ldap = "@Value(_ldap)"
      where email = "@Value(email)" limit 1

Bookmark: Employee Deactivation DB tasks
Note: set deactivated date
SQLExecutor_2
    COMBINE_ATTRS = Result Attributes Only
    COMBINE_GEOM = Initiator Geometry Only
    DATASET = set-rds-user
    FORMAT = MYSQL
    MYSQL_NAMED_CONNECTION = set-rds-user
    OUTPUT_FEATURES_DISPLAY = Schema and Data Features
    SQL_STATEMENT:
      update users.ukg_users
      set deactivated = NOW()
      where id = @Value(id)
Note: notify techops_automation of employee deactivations
HTTPCaller_3
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - Employee deactivated",
              "text": "Employee @Value(id) (@Value(first) @Value(last))",
              "color": "danger"
          }
          ]
      }
    UPLOAD_CONTENT_TYPE = Text (text/plain)
    UPLOAD_TYPE = Specify Upload Body
    USE_COOKIES = No
    VERIFY_SSL_CERTIFICATES = Yes

Bookmark: org
Note: Only process the most recent two files
Sampler_2
    RATE = 2
    SAMPLE_MODE = No
    SAMPLE_TYPE_LONG = First N Features
    SAMPLED -> Counter_2
Counter_2
    CNT_ATTR = _count
    DOMAIN = counter
    SCOPE = Local
    START = 0
    -> GoogleDriveConnector_3
    -> Logger_2
Note: download csv files
GoogleDriveConnector_3
    GOOGLEDRIVE_NAMED_CONNECTION = ellaine.chan Google Drive
    OPERATION_TYPE = Download
    PARAMETER_SETUP = _FME_FILES;@Value(_id);_FME_DATA_TARGET;Attribute;_FME_TARGET_FOLDER;<Unused>;_FME_INCLUDE_SUBFOLDERS;<Unused>;_FME_TARGET_ATTRIBUTE;_contents;FME_CONTROLLER_QUERY_FILE;transformers/dependencies/googledrive/Download.fme;FME_CONTROLLER_CHOICE;Download
    -> Tester_11
Tester_11
    BOOL_OP = OR
    TEST_CLAUSE = TEST @Value(_count) = 0
    TEST_MODE = TEST
    PASSED -> TempPathnameCreator_3
    FAILED -> TempPathnameCreator_4
TempPathnameCreator_3
    EXTENSION = .csv
    PATHNAME_ATTR = _pathname
    -> AttributeFileWriter_2
Note: latest version
AttributeFileWriter_2
    CHAR_ENCODING = fme-system
    FILE_NAME = @Value(_pathname)
    OVERWRITE_FILE = Overwrite file
    SOURCE_ATTR = _contents
    -> FeatureReader_2 [INITIATOR]
FeatureReader_2
    ATTRS_TO_EXPOSE = OL1 Code OL1 Name OL1 Manager Email OL2 Code OL2 Name OL2 Manager Email OL3 Code OL3 Name OL3 Alt Name Org Level 3 Manager's Email
    ATTR_ACCUM_MODE = Only Use Result
    COMBINE_GEOM = Use Result
    CSV2_CASE_SENSITIVE_FIELD_NAMES = Yes
    CSV2_CHUNK_SIZE = 100000
    CSV2_DATA_START_LINE = 2
    CSV2_DELIMITER = auto
    CSV2_ENCODING = UTF-8
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 10000
    CSV2_SCAN_TYPES = Yes
    CSV2_SKIP_DUPLICATE_DELIMITERS = No
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_USE_CUSTOM_SCHEMA = NO
    DATASET = @Value(_pathname)
    FORMAT = CSV2
    INTERACT = NONE
    OUTPUT_FEATURES_DISPLAY = Schema and Data Features
    <OTHER> -> AttributeManager_5
    <REJECTED> -> Terminator_2
AttributeManager_5
    ATTR_TABLE = SET_TO state = new
    -> Tester_4
    -> Tester_5
    -> Tester_3
TempPathnameCreator_4
    EXTENSION = .csv
    PATHNAME_ATTR = _pathname
    -> AttributeFileWriter_4
Note: older version
AttributeFileWriter_4
    CHAR_ENCODING = fme-system
    FILE_NAME = @Value(_pathname)
    OVERWRITE_FILE = Overwrite file
    SOURCE_ATTR = _contents
    -> FeatureReader_4 [INITIATOR]
FeatureReader_4
    ATTRS_TO_EXPOSE = OL1 Code OL1 Name OL1 Manager Email OL2 Code OL2 Name OL2 Manager Email OL3 Code OL3 Name OL3 Alt Name Org Level 3 Manager's Email
    ATTR_ACCUM_MODE = Only Use Result
    COMBINE_GEOM = Use Result
    CSV2_CASE_SENSITIVE_FIELD_NAMES = Yes
    CSV2_CHUNK_SIZE = 100000
    CSV2_DATA_START_LINE = 2
    CSV2_DELIMITER = auto
    CSV2_ENCODING = UTF-8
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 10000
    CSV2_SCAN_TYPES = Yes
    CSV2_SKIP_DUPLICATE_DELIMITERS = No
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_USE_CUSTOM_SCHEMA = NO
    DATASET = @Value(_pathname)
    FORMAT = CSV2
    INTERACT = NONE
    OUTPUT_FEATURES_DISPLAY = Schema and Data Features
    <OTHER> -> AttributeManager_6
    <REJECTED> -> Terminator_2
Terminator_2
    MESSAGE = Translation Terminated
AttributeManager_6
    ATTR_TABLE = SET_TO state = old
    -> Tester_3
    -> Tester_4
    -> Tester_5
Note: Process Org 1 columns
Tester_3
    BOOL_OP = OR
    TEST_CLAUSE = TEST OL1 Code ATTRIBUTE_HAS_A_VALUE ""
    TEST_MODE = TEST
    PASSED -> AttributeManager_2
Note: Process Org 2 columns
Tester_4
    BOOL_OP = OR
    TEST_CLAUSE = TEST OL2 Code ATTRIBUTE_HAS_A_VALUE ""
    TEST_MODE = TEST
    PASSED -> NullAttributeMapper_4
Note: If no manager value, use org1 manager
NullAttributeMapper_4
    ATTRCHOICE = Selected Attributes
    ATTRLIST = OL2 Manager Email
    NEW_VALUE = @Value(OL1 Manager Email)
    NULL_TREATMENT = New Value
    SOURCE_ATTR_VAL = Null
    -> AttributeManager_3
Note: Process Org 3 columns
Tester_5
    BOOL_OP = OR
    TEST_CLAUSE = TEST OL3 Code ATTRIBUTE_HAS_A_VALUE ""
    TEST_MODE = TEST
    PASSED -> NullAttributeMapper_5
Note: If no org 2 manager value, use org1 manager
NullAttributeMapper_5
    ATTRCHOICE = Selected Attributes
    ATTRLIST = OL2 Manager Email
    NEW_VALUE = @Value(OL1 Manager Email)
    NULL_TREATMENT = New Value
    SOURCE_ATTR_VAL = Null
    -> NullAttributeMapper_3
Note: If no org 3 manager value, use org2 manager
NullAttributeMapper_3
    ATTRCHOICE = Selected Attributes
    ATTRLIST = Org Level 3 Manager's Email
    NEW_VALUE = @Value(OL2 Manager Email)
    NULL_TREATMENT = New Value
    SOURCE_ATTR_VAL = Null
    -> AttributeManager_4
DuplicateFilter
    INPUT_ORDERED_CHOICE = No
    KEYATTR = id state
    UNIQUE -> FeatureMerger [REQUESTOR]
Logger_2
    LOG_FEATURE = LOG_ONLY
    MAXCOORDS = 20
    MAXFEATS = 20
    MESSAGE = Downloading... @Value(_name)
    SEVERITY = INFO
SQLCreator_3
    DATASET = set-rds-user
    EXPOSED_ATTRIBUTE_LIST = email,lead_id
    FORMAT = MYSQL
    MYSQL_HANDLE_UTC_OFFSET = Yes
    MYSQL_NAMED_CONNECTION = set-rds-user
    MYSQL_QUERY_FEATURE_TYPES_FOR_MERGE_FILTERS = Yes
    OUTPUT_FEATURES_DISPLAY = Schema and Data Features
    SQL_STATEMENT = SELECT email, id as lead_id from users.ukg_users
    RESULT -> FeatureMerger [SUPPLIER]
Note: merge in team lead ids
FeatureMerger
    ATTR_ACCUM_MODE = Merge Supplier
    ATTR_CONFLICT_RES = Use Requestor
    IGNORE_NULLS = No
    JOIN_KEYS = @ReplaceString(@Value(team_lead),"@safe.com","") @Value(email) AUTO
    MERGE_TYPE = Attributes Only
    PROCESS_DUPS = NO
    REJECT_NULL_MISSING_KEYS = No
    SUPPLIERS_FIRST = No
    MERGED -> SQLExecutor_3 [INITIATOR]
    MERGED -> Tester_12
    UNMERGED_REQUESTOR -> SQLExecutor_10 [INITIATOR]
    UNMERGED_REQUESTOR -> Tester_12
Tester_12
    BOOL_OP = OR
    TEST_CLAUSE = TEST @Value(state) = old
    TEST_MODE = TEST
    PASSED -> ChangeDetector_2 [ORIGINAL]
    FAILED -> ChangeDetector_2 [REVISED]
ChangeDetector_2
    BLANK_AND_MISSING_DIFFER = No
    BLANK_AND_MISSING_NAMES_TRAITS_DIFFER = No
    CHECK_COORDINATE_SYSTEMS = No
    CHECK_TYPES_AND_ENCODINGS = No
    LENIENT_MATCH = No
    MATCH = FULL
    MATCHATTRS = alt_name name parent_id team_lead
    MATCH_STRATEGY = Match Selected Attributes
    PREEMPTIVE_ATTRS = id
    UNCHANGED_OUTPUT = Output Original
    UPDATED_LIST_NAME = _org_change_list
    UPSERT_MODE = No
    UPDATED -> ListExploder_2
    INSERTED -> HTTPCaller_5
    INSERTED -> AttributeCreator_3
    DELETED -> SQLExecutor_5 [INITIATOR]
    DELETED -> HTTPCaller_6
ListExploder_2
    ATTR_ACCUM_MODE = Merge List Attributes
    ATTR_CONFLICT_RES = Use List Attribute Values
    INDEX_ATTR = _element_index
    LIST_ATTR = _org_change_list{}
    ELEMENTS -> NullAttributeMapper_2
NullAttributeMapper_2
    ATTRCHOICE = Selected Attributes
    ATTRLIST = originalValue revisedValue
    NEW_VALUE = Null
    NULL_TREATMENT = New Value
    SOURCE_ATTR_VAL = Null Empty "Missing (Selected Attributes Only)"
    -> HTTPCaller_2
    -> AttributeCreator_12
Note: notify techops_automation of any changes
HTTPCaller_2
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - Team Updated",
              "text": "Team ID: @Value(id) (@Value(name))\nField: @Value(attributeName)\n@Value(originalValue) -> @Value(revisedValue)",
              "color": "warning"
          }
          ]
      }
    UPLOAD_CONTENT_TYPE = Text (text/plain)
    UPLOAD_TYPE = Specify Upload Body
    USE_COOKIES = No
    VERIFY_SSL_CERTIFICATES = Yes
AttributeCreator_12
    ATTR_TABLE:
      SET_TO CHANGE = UPDATE
      SET_TO OLD_NAME = @Value(originalValue)
      SET_TO NEW_NAME = @Value(revisedValue)
    -> TeamDelta (writer AUTOMATIONS_1)
AttributeCreator_3
    ATTR_TABLE:
      SET_TO CHANGE = ADD
      SET_TO NEW_NAME = @Value(name)
    -> TeamDelta (writer AUTOMATIONS_1)
TeamDelta (writer AUTOMATIONS_1)
    attributes: NEW_NAME string, OLD_NAME string, CHANGE string, ORG_LEVEL string
SQLExecutor_5
    COMBINE_ATTRS = Result Attributes Only
    COMBINE_GEOM = Initiator Geometry Only
    DATASET = set-rds-user
    FORMAT = MYSQL
    MYSQL_HANDLE_UTC_OFFSET = Yes
    MYSQL_NAMED_CONNECTION = set-rds-user
    MYSQL_QUERY_FEATURE_TYPES_FOR_MERGE_FILTERS = Yes
    OUTPUT_FEATURES_DISPLAY = Schema and Data Features
    SQL_STATEMENT:
      UPDATE users.ukg_teams
      SET archived = NOW()
      WHERE id = "@Value(id)"
Note: notify techops_automation of new teams
HTTPCaller_5
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - Team Added",
              "text": "Team ID: @Value(id) (@Value(name))",
              "color": "good"
          }
          ]
      }
    UPLOAD_CONTENT_TYPE = Text (text/plain)
    UPLOAD_TYPE = Specify Upload Body
    USE_COOKIES = No
    VERIFY_SSL_CERTIFICATES = Yes
Note: notify techops_automation of team deactivations
HTTPCaller_6
    CONNECTION_TIMEOUT_LENGTH = 60
    ERROR_ATTR = _error
    FOLLOW_REDIRECTS = FOLLOW_WITH_GET
    HTTP_METHOD = POST
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(SLACK_NOTIFICATION_WEBHOOK)
    TRANSFER_TIMEOUT_LENGTH = 90
    UPLOAD_BODY:
      {
          "attachments": [{
              "title": "HRIS - Team Deactivated",
              "text": "Team ID: @Value(id) (@Value(name))",
              "color": "danger"
          }
          ]
      }
    UPLOAD_CONTENT_TYPE = Text (text/plain)
    UPLOAD_TYPE = Specify Upload Body
    USE_COOKIES = No
    VERIFY_SSL_CERTIFICATES = Yes
Note: insert/update team with lead_id
SQLExecutor_3
    ATTR_IGNORE_NULLS = No
    COMBINE_ATTRS = Keep Initiator Attributes if Conflict
    COMBINE_GEOM = Initiator Geometry Only
    DATASET = set-rds-user
    FORMAT = MYSQL
    MYSQL_HANDLE_UTC_OFFSET = Yes
    MYSQL_NAMED_CONNECTION = set-rds-user
    MYSQL_QUERY_FEATURE_TYPES_FOR_MERGE_FILTERS = Yes
    OUTPUT_FEATURES_DISPLAY = Schema and Data Features
    SQL_STATEMENT:
      INSERT INTO users.ukg_teams (id, name, alt_name, parent_id, lead_id, last_update, org_level) VALUES("@Value(id)", "@Value(name)", "@Value(alt_name)", "@Value(parent_id)", @Value(lead_id), NOW(), @Value(org_level))
      ON DUPLICATE KEY UPDATE
      name = "@Value(name)", alt_name = "@Value(alt_name)", lead_id = @Value(lead_id), parent_id = "@Value(parent_id)", org_level = @Value(org_level), last_update=NOW();
Note: insert/update team with no lead_id
SQLExecutor_10
    ATTR_IGNORE_NULLS = No
    COMBINE_ATTRS = Keep Initiator Attributes if Conflict
    COMBINE_GEOM = Initiator Geometry Only
    DATASET = set-rds-user
    FORMAT = MYSQL
    MYSQL_NAMED_CONNECTION = set-rds-user
    OUTPUT_FEATURES_DISPLAY = Schema and Data Features
    SQL_STATEMENT:
      INSERT INTO users.ukg_teams (id, name, alt_name, parent_id, last_update, org_level) VALUES("@Value(id)", "@Value(name)", "@Value(alt_name)", "@Value(parent_id)", NOW(), @Value(org_level))
      ON DUPLICATE KEY UPDATE
      name = "@Value(name)", alt_name = "@Value(alt_name)", parent_id = "@Value(parent_id)", last_update=NOW(), org_level = @Value(org_level);

Bookmark: Rename attributes t…e unused attributes
Note: Rename attributes to match ukg_org table col names, remove unused attributes, add org_level attribute
AttributeManager_2
    ATTR_TABLE:
      RENAME_SET_VALUE OL1 Code > id
      RENAME_SET_VALUE OL1 Name > name
      RENAME_SET_VALUE OL1 Manager Email > team_lead
      REMOVE OL2 Code
      REMOVE OL2 Name
      REMOVE OL2 Manager Email
      REMOVE OL3 Code
      REMOVE OL3 Name
      REMOVE OL3 Alt Name
      REMOVE Org Level 3 Manager's Email
      SET_TO org_level = 1
      SET_TO
    -> DuplicateFilter
AttributeManager_3
    ATTR_TABLE:
      RENAME_SET_VALUE OL1 Code > parent_id
      REMOVE OL1 Name
      REMOVE OL1 Manager Email
      RENAME_SET_VALUE OL2 Code > id
      RENAME_SET_VALUE OL2 Name > name
      RENAME_SET_VALUE OL2 Manager Email > team_lead
      REMOVE OL3 Code
      REMOVE OL3 Name
      REMOVE OL3 Alt Name
      REMOVE Org Level 3 Manager's Email
      SET_TO org_level = 2
    -> DuplicateFilter
AttributeManager_4
    ATTR_TABLE:
      REMOVE OL1 Code
      REMOVE OL1 Name
      REMOVE OL1 Manager Email
      RENAME_SET_VALUE OL2 Code > parent_id
      REMOVE OL2 Name
      REMOVE OL2 Manager Email
      RENAME_SET_VALUE OL3 Code > id
      RENAME_SET_VALUE OL3 Name > name
      RENAME_SET_VALUE OL3 Alt Name > alt_name
      RENAME_SET_VALUE Org Level 3 Manager's Email > team_lead
      SET_TO org_level = 3
    -> DuplicateFilter
